--/************************************************************************ 
--*                                                                       * 
--*  Copyright (c) 1998-2004 Intel Corporation. All Rights Reserved.      * 
--*                                                                       * 
--* Redistribution and use in source and binary forms, with or without    * 
--* modification, are permitted provided that the following conditions    * 
--* are met:                                                              * 
--*                                                                       * 
--*   a.. Redistributions of source code must retain the above copyright  * 
--*       notice, this list of conditions and the following disclaimer.   * 
--*   b.. Redistributions in binary form must reproduce the above         * 
--*       copyright notice, this list of conditions and the following     * 
--*       disclaimer in the documentation and/or other materials provided * 
--*       with the distribution.                                          * 
--*   c.. Neither the name of Intel Corporation nor the names of its      * 
--*       contributors may be used to endorse or promote products derived * 
--*       from this software without specific prior written permission.   * 
--*                                                                       * 
--* THIS SOFTWARE IS PROVIDED BY THE COPYRIGHT HOLDERS AND CONTRIBUTORS   * 
--* "AS IS" AND ANY EXPRESS OR IMPLIED WARRANTIES, INCLUDING, BUT NOT     * 
--* LIMITED TO, THE IMPLIED WARRANTIES OF MERCHANTABILITY AND FITNESS FOR * 
--* A PARTICULAR PURPOSE ARE DISCLAIMED. IN NO EVENT SHALL THE COPYRIGHT  * 
--* OWNER OR CONTRIBUTORS BE LIABLE FOR ANY DIRECT, INDIRECT, INCIDENTAL, * 
--* SPECIAL, EXEMPLARY, OR CONSEQUENTIAL DAMAGES (INCLUDING, BUT NOT      * 
--* LIMITED TO, PROCUREMENT OF SUBSTITUTE GOODS OR SERVICES; LOSS OF USE, * 
--* DATA, OR PROFITS; OR BUSINESS INTERRUPTION) HOWEVER CAUSED AND ON     * 
--* ANY THEORY OF LIABILITY, WHETHER IN CONTRACT, STRICT LIABILITY, OR    * 
--* TORT (INCLUDING NEGLIGENCE OR OTHERWISE) ARISING IN ANY WAY OUT OF    * 
--* THE USE OF THIS SOFTWARE, EVEN IF ADVISED OF THE POSSIBILITY OF SUCH  * 
--* DAMAGE.                                                               * 
--*                                                                       * 
--************************************************************************* 
--* Name                        : IntelligentServerAlertEvents.mib 
--* Description	                : MIB file for PET events 
--* Created                     : Wesdnesday, December 17, 2003 
--* Author                      : Intel Corporation 
--*  
--* $History:$  
--* 
--*             Date                    : March 7th,2002  
--*             Changed by              :  
--*             Change DESCRIPTION: Updated MIB file  
--*							   
--*             Date                    : December 17th,2003  
--*             Changed by              :  
--*             Change DESCRIPTION      : Started with ASF MIB file 
--*                                        
--*************************************************************************/ 

--******************************************************************* 
--******************************************************************** 
--****                                                              ** 
--****    (C)Copyright 2011-2012, American Megatrends Inc.          ** 
--****                                                              ** 
--****    All Rights Reserved.                                      ** 
--****                                                              ** 
--****    5555 , Oakbrook Pkwy, Norcross,                           ** 
--****                                                              ** 
--****    Georgia - 30093, USA. Phone-(770)-246-8600.               ** 
--****                                                              ** 
--******************************************************************** 
--******************************************************************** 
--* Name                        : PETTrap.mib 
--* Description	                : Contains MIB for all standard sensor types 
--* Created                     : 8th August, 2011 
--* Author                      : AMI 
--*                                        
--*************************************************************************/ 

--********************************************************************************************
--Release Note:
--version  time		author   	note
--v1.0     20110808     AMI      	Contains MIB for all standard sensor types 
--v1.1     20140801     -wxl	add immtrapg and its children
--v1.2	   20141010     -wxl	fix insert hdd alert remove, remove hdd alert insert.
--v1.3     20141021	-wxl	add oem MemError and CPUERROR; modify enterprises id from 3183 to 37945
--v1.4	   20150310	-wxl	Remove "_", for linux cmd line error to load mib.
--v2.4	   20190731	-hlc	For Grammatical correction.
--v2.4	   20190830	-hlc	For Add OBJECTS info.
--v2.4	   20190902	-hlc	For Add SEVERITY info.
--v2.4	   20190912	-hlc	For Add V1 Object info.
--v2.5	   20191031	-hlc	Add trapID 487303.
--v3.0	   20201219	-zhc	Add some trapID.
--v3.1	   20210101	-zhc	Add trapID 66002 460721 265089 264961 263937 264065.
--v3.2	   20210114	-zhc	Add trapID 66000 65872 1901313.
--v3.3	   20210128	-zhc  Just used for V1(TRAP-TYPE).
--********************************************************************************************/ 
INTELLIGENT-SERVER-TRAP-EVENTS DEFINITIONS ::=  BEGIN 

    IMPORTS 
        enterprises 
            FROM RFC1155-SMI
        OBJECT-TYPE
			FROM RFC-1212 
       	TRAP-TYPE
		    FROM RFC-1215
		DisplayString 
			FROM RFC1213-MIB; 

    IntelligentServer     OBJECT IDENTIFIER ::=  { enterprises 37945 } 

    IntelligentServerBMC MODULE-IDENTITY
              LAST-UPDATED  "201910310000Z"
              ORGANIZATION  ""
              CONTACT-INFO
                            "Zip:250101   E-mail:support@ieisystem.com "    
              DESCRIPTION
                            "The INPUR-SERVER-BMC-MIB contains objects to Manage the server."
              ::= { IntelligentServer 1 }
-- ****************************************
-- SYSTEM INFORMATION BRANCH STARTS HERE. 
-- ****************************************
    IntelligentServerTrap OBJECT IDENTIFIER ::=  { IntelligentServerBMC 1 } 
    IntelligentServerTrapVar OBJECT IDENTIFIER ::= { IntelligentServerTrap 1 }
--  IntelligentServer        = .1.3.6.1.4.1.37945
--  IntelligentServerBMC     = .1.3.6.1.4.1.37945.1 
--  IntelligentServerTrap    = .1.3.6.1.4.1.37945.1.1 
--  IntelligentServerTrapVar = .1.3.6.1.4.1.37945.1.1.1

        altTrapTime OBJECT-TYPE
                    SYNTAX  DisplayString
                    MAX-ACCESS read-only
                    STATUS current
                    DESCRIPTION
                        "Trap Time"
                    ::=  { IntelligentServerTrapVar 1 }

        altSpTxtId  OBJECT-TYPE
                    SYNTAX  DisplayString
                    MAX-ACCESS read-only
                    STATUS current
                    DESCRIPTION
                        "Trap SystemID"
                    ::=  { IntelligentServerTrapVar 3 }
                       
        altSysSern  OBJECT-TYPE
                    SYNTAX  DisplayString
                    ACCESS  read-only
                    STATUS  mandatory
                    DESCRIPTION
                        "Trap Product SN"
                    ::=  { IntelligentServerTrapVar 6 }
        
        altPriority OBJECT-TYPE
                    SYNTAX  INTEGER
                            {
                            Information(0),
                            Warning(1),
                            Critical(2),
                            Recovery(8)
                            }
                    MAX-ACCESS read-only
                    STATUS current
                    DESCRIPTION
                            "Trap severity
                            - Information(0)
                            - Warning(1)
                            - Critical(2)
                            - Recovery(8)"
                    ::=  { IntelligentServerTrapVar 8 }

        altHostContact OBJECT-TYPE
                    SYNTAX  DisplayString
                    MAX-ACCESS read-only
                    STATUS current
                    DESCRIPTION
                    "Trap Host Contact"
                    ::=  { IntelligentServerTrapVar 12 }

        altHostLocation OBJECT-TYPE
                    SYNTAX  DisplayString
                    MAX-ACCESS read-only
                    STATUS current
                    DESCRIPTION
                        "Trap Host Location"
                    ::=  { IntelligentServerTrapVar 13 }

        altSysManufacture OBJECT-TYPE 
                    SYNTAX  DisplayString 
                    MAX-ACCESS read-only
                    STATUS current 
                    DESCRIPTION
                    "Manufacture name" 
                    ::=  { IntelligentServerTrapVar 24 }

        altSysModel OBJECT-TYPE 
                    SYNTAX  DisplayString 
                    MAX-ACCESS read-only
                    STATUS current
                    DESCRIPTION
                        "System model" 
                    ::=  { IntelligentServerTrapVar 25 } 

        altSensorName OBJECT-TYPE 
                    SYNTAX  DisplayString 
                    MAX-ACCESS read-only
                    STATUS current
                    DESCRIPTION
                        "Sensor Name" 
                    ::=  { IntelligentServerTrapVar 26 } 

        altSensorType OBJECT-TYPE 
                    SYNTAX  DisplayString 
                    MAX-ACCESS read-only
                    STATUS current
                    DESCRIPTION
                        "Sensor Type" 
                    ::=  { IntelligentServerTrapVar 27 }

        altSensorReading OBJECT-TYPE 
                    SYNTAX  DisplayString 
                    MAX-ACCESS read-only
                    STATUS current
                    DESCRIPTION
                        "Current Sensor Reading" 
                    ::=  { IntelligentServerTrapVar 28 }  

        altSensorThreshold OBJECT-TYPE 
                    SYNTAX  DisplayString 
                    MAX-ACCESS read-only
                    STATUS current
                    DESCRIPTION
                        "Sensor Threshold: 
                         LowerNonRecoverable, LowerCritical, LowerNonCritical, 
                         UpperNonCritical, UpperCritical, UpperNonRecoverable" 
                    ::=  { IntelligentServerTrapVar 29 }  

        altBMCHostName   OBJECT-TYPE 
                    SYNTAX  DisplayString 
                    MAX-ACCESS read-only
                    STATUS current 
                    DESCRIPTION
                        "BMC Host Name" 
                    ::=  { IntelligentServerTrapVar 32 } 


        altSysboard OBJECT-TYPE 
                    SYNTAX  DisplayString 
                    MAX-ACCESS read-only
                    STATUS current
                    DESCRIPTION
                        "Board name." 
                    ::=  { IntelligentServerTrapVar 33 } 

        altSysboardType  OBJECT-TYPE 
                    SYNTAX  DisplayString 
                    MAX-ACCESS read-only
                    STATUS current
                    DESCRIPTION
                        "Board Type" 
                    ::=  { IntelligentServerTrapVar 34 } 

       altSysboardstatus OBJECT-TYPE 
                    SYNTAX  DisplayString 
                    MAX-ACCESS read-only
                    STATUS current
                    DESCRIPTION
                        "Board Status" 
                    ::=  { IntelligentServerTrapVar 35 } 

       altSysName   OBJECT-TYPE 
                    SYNTAX  DisplayString 
                    MAX-ACCESS read-only
                    STATUS current
                    DESCRIPTION
                        "System Name" 
                    ::=  { IntelligentServerTrapVar 36 } 
					  
       altEventSeverity OBJECT-TYPE 
                    SYNTAX  DisplayString 
                    MAX-ACCESS read-only
                    STATUS current
                    DESCRIPTION 
                        "Event Severity" 
                    ::=  { IntelligentServerTrapVar 37 } 
					  
       altEventDescription OBJECT-TYPE 
                    SYNTAX  DisplayString 
                    MAX-ACCESS read-only
                    STATUS current
                    DESCRIPTION
                        "Event Description" 
                    ::=  { IntelligentServerTrapVar 38 } 
                    
       altEventAssertOrDeassert OBJECT-TYPE 
                    SYNTAX  DisplayString 
                    MAX-ACCESS read-only
                    STATUS current
                    DESCRIPTION 
                        "Event Assert Or Deassert" 
                    ::=  { IntelligentServerTrapVar 42 } 

-- **********************************************
-- ******  IntelligentServerServerTRAPObject  Begin   ******
-- **********************************************
    IntelligentServerServerTRAPObject OBJECT IDENTIFIER ::= { IntelligentServerBMC 1 }

-- **********************************************
-- *Test                                        * 
-- **********************************************
    IntelligentServerTrapTest TRAP-TYPE
        STATUS current
        ENTERPRISE IntelligentServerServerTRAPObject
        DESCRIPTION
            "Trap Test for IntelligentServer SNMP(V1)"
        --#SUMMARY    "Trap Test for IntelligentServer SNMP(V1)" 
        --#SEVERITY   INFORMATION
        ::= 0
    IntelligentServerTrapTest-V2cV3 NOTIFICATION-TYPE
        STATUS current
        DESCRIPTION
            "Trap Test for IntelligentServer SNMP(V2/V3)"
        --#SUMMARY    "Trap Test for IntelligentServer SNMP(V2/V3)" 
        --#SEVERITY   INFORMATION
        ::= { IntelligentServerServerTRAPObject 0 }

-- **********************************************
-- *Temperature                                 *
-- **********************************************
--  Temperature has decreased below lower non-critical threshold
    IntelligentServerUnderTemperatureWarningLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Under-Temperature Warning (Lower non-critical, going low)"
        --#SEVERITY   INFORMATION
        ::= 65792
    IntelligentServerUnderTemperatureWarningLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Under-Temperature Warning (Lower non-critical, going low)"
        --#SEVERITY   INFORMATION
        ::= { IntelligentServerServerTRAPObject 65792 }

--  Temperature has increased above lower non-critical threshold
    IntelligentServerUnderTemperatureWarningHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Under-Temperature Warning (Lower non-critical, going high)"
        --#SEVERITY   WARNING
        ::= 65793
    IntelligentServerUnderTemperatureWarningHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Under-Temperature Warning (Lower non-critical, going high)"
        --#SEVERITY   WARNING
        ::= { IntelligentServerServerTRAPObject 65793 }

--  Temperature has decreased below lower critical threshold
    IntelligentServerUnderTemperatureCriticalLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Temperature problem (Lower critical, going low)"       
        --#SEVERITY  INFORMATION 
        ::= 65794
    IntelligentServerUnderTemperatureCriticalLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Temperature problem (Lower critical, going low)"       
        --#SEVERITY  INFORMATION 
        ::= { IntelligentServerServerTRAPObject 65794 }
 
 -- Temperature has increased above lower critical threshold
     IntelligentServerUnderTemperatureCriticalHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Temperature problem (Lower critical, going high)"
        --#SEVERITY  INFORMATION 
        ::= 65795
    IntelligentServerUnderTemperatureCriticalHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Temperature problem (Lower critical, going high)"
        --#SEVERITY  INFORMATION 
        ::= { IntelligentServerServerTRAPObject 65795 }
 
 -- Temperature has decreased below lower non-recoverable threshold 
     IntelligentServerUnderTemperatureNonRecoverableLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Temperature problem (Lower non-recoverable, going low)"       
        --#SEVERITY   INFORMATION 
        ::= 65796
    IntelligentServerUnderTemperatureNonRecoverableLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Temperature problem (Lower non-recoverable, going low)"       
        --#SEVERITY   INFORMATION 
        ::= { IntelligentServerServerTRAPObject 65796 }
 
 -- Temperature has increased above lower non-recoverable threshold
     IntelligentServerUnderTemperatureNonRecoverableHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Under-Temperature problem (Lower non-recoverable, going high)"
        --#SEVERITY CRITICAL
            ::= 65797
    IntelligentServerUnderTemperatureNonRecoverableHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Under-Temperature problem (Lower non-recoverable, going high)"
        --#SEVERITY CRITICAL
            ::= { IntelligentServerServerTRAPObject 65797 }
 
--  Temperature has decreased below Upper non-critical threshold
    IntelligentServerOverTemperatureWarningLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Over-Temperature Warning (Upper non-critical, going low)"        
        --#SEVERITY   INFORMATION
        ::= 65798
    IntelligentServerOverTemperatureWarningLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Over-Temperature Warning (Upper non-critical, going low)"        
        --#SEVERITY   INFORMATION
        ::= { IntelligentServerServerTRAPObject 65798 }
 
--  Temperature has increased above upper non-critical threshold.
    IntelligentServerOverTemperatureWarningHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
          "Over-Temperature Warning (Upper non-critical, going high)" 
        --#SEVERITY   WARNING
        ::= 65799
    IntelligentServerOverTemperatureWarningHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
          "Over-Temperature Warning (Upper non-critical, going high)" 
        --#SEVERITY   WARNING
        ::= { IntelligentServerServerTRAPObject 65799 }
 
-- Temperature has decreased below Upper critical threshold 
    IntelligentServerOverTemperatureCriticalLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Temperature problem (Upper critical, going low)"
        --#SEVERITY INFORMATION
        ::= 65800
    IntelligentServerOverTemperatureCriticalLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Temperature problem (Upper critical, going low)"
        --#SEVERITY INFORMATION
        ::= { IntelligentServerServerTRAPObject 65800 }
 
 -- Temperature has increased above Upper critical threshold ]
     IntelligentServerOverTemperatureCriticalHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Temperature problem (Upper critical, going high)" 
        --#SEVERITY CRITICAL
        ::= 65801
    IntelligentServerOverTemperatureCriticalHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Temperature problem (Upper critical, going high)" 
        --#SEVERITY CRITICAL
        ::= { IntelligentServerServerTRAPObject 65801 }
 
 -- Temperature has decreased below Upper non-recoverable threshold 
    IntelligentServerOverTemperatureNonRecoverableLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Temperature problem (Upper non-recoverable, going low)" 
        --#SEVERITY INFORMATION
        ::= 65802
    IntelligentServerOverTemperatureNonRecoverableLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Temperature problem (Upper non-recoverable, going low)" 
        --#SEVERITY INFORMATION
        ::= { IntelligentServerServerTRAPObject 65802 }
 
 -- Temperature has increased above Upper non-recoverable threshold 
    IntelligentServerOverTemperatureNonRecoverableHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Temperature problem (Upper non-recoverable, going high)" 
        --#SEVERITY CRITICAL
        ::= 65803
    IntelligentServerOverTemperatureNonRecoverableHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Temperature problem (Upper non-recoverable, going high)" 
        --#SEVERITY CRITICAL
        ::= { IntelligentServerServerTRAPObject 65803 }
  
 -- DTS Temperature Lower non-critical going low asserted
    IntelligentServerDTSTemperatureLowerNonCriticalGoingLowAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Lower non-critical going low asserted" 
        --#SEVERITY CRITICAL
        ::= 65872
    IntelligentServerDTSTemperatureLowerNonCriticalGoingLowAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Lower non-critical going low asserted" 
        --#SEVERITY CRITICAL
        ::= { IntelligentServerServerTRAPObject 65872 }
              
 -- DTS Temperature Lower critical going low asserted
    IntelligentServerDTSTemperatureLowerCriticalGoingLowAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Lower critical going low asserted" 
        --#SEVERITY CRITICAL
        ::= 65874
    IntelligentServerDTSTemperatureLowerCriticalGoingLowAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Lower critical going low asserted" 
        --#SEVERITY CRITICAL
        ::= { IntelligentServerServerTRAPObject 65874 }
 
-- Temperature decreased below lower non-critical threshold Cleared 
   IntelligentServerUnderTemperatureWarningLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Under-Temperature Warning (Lower non-critical, going low) Cleared"
        --#SEVERITY INFORMATION
        ::= 65920
    IntelligentServerUnderTemperatureWarningLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Under-Temperature Warning (Lower non-critical, going low) Cleared"
        --#SEVERITY INFORMATION
        ::= { IntelligentServerServerTRAPObject 65920 }
 
-- Temperature increased above lower non-critical threshold Cleared 
    IntelligentServerUnderTemperatureWarningHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Under-Temperature Warning (Lower non-critical, going high)Cleared"
        --#SEVERITY INFORMATION
        ::= 65921
    IntelligentServerUnderTemperatureWarningHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Under-Temperature Warning (Lower non-critical, going high)Cleared"
        --#SEVERITY INFORMATION
        ::= { IntelligentServerServerTRAPObject 65921 }
 
-- Temperature decreased below lower critical threshold Cleared 
    IntelligentServerUnderTemperatureCriticalLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Under-Temperature problem (Lower critical, going low)Cleared" 
        --#SEVERITY INFORMATION
        ::= 65922
    IntelligentServerUnderTemperatureCriticalLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Under-Temperature problem (Lower critical, going low)Cleared" 
        --#SEVERITY INFORMATION
        ::= { IntelligentServerServerTRAPObject 65922 }
 
 -- Temperature increased above lower critical threshold Cleared 
     IntelligentServerUnderTemperatureCriticalHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Temperature problem (Lower critical, going high) Cleared" 
        --#SEVERITY CRITICAL
        ::= 65923
    IntelligentServerUnderTemperatureCriticalHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Temperature problem (Lower critical, going high) Cleared" 
        --#SEVERITY CRITICAL
        ::= { IntelligentServerServerTRAPObject 65923 }
 
 -- Temperature decreased below lower non-recoverable threshold Cleared 
     IntelligentServerUnderTemperatureNonRecoverableLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Temperature problem (Lower non-recoverable, going low)Cleared" 
        --#SEVERITY INFORMATION
        ::= 65924
    IntelligentServerUnderTemperatureNonRecoverableLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Temperature problem (Lower non-recoverable, going low)Cleared" 
        --#SEVERITY INFORMATION
        ::= { IntelligentServerServerTRAPObject 65924 }
 
 -- Temperature increased above lower non-recoverable threshold Cleared 
     IntelligentServerUnderTemperatureNonRecoverableHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Temperature problem (Lower non-recoverable, going high) Cleared" 
        --#SEVERITY INFORMATION
        ::= 65925
    IntelligentServerUnderTemperatureNonRecoverableHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Temperature problem (Lower non-recoverable, going high) Cleared" 
        --#SEVERITY INFORMATION
        ::= { IntelligentServerServerTRAPObject 65925 }
 
--  Temperature decreased below Upper non-critical threshold Cleared 
    IntelligentServerOverTemperatureWarningLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Over-Temperature Warning (Upper non-critical, going low) Cleared" 
        --#SEVERITY INFORMATION
        ::= 65926
    IntelligentServerOverTemperatureWarningLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Over-Temperature Warning (Upper non-critical, going low) Cleared" 
        --#SEVERITY INFORMATION
        ::= { IntelligentServerServerTRAPObject 65926 }
 
--  Temperature increased above upper non-critical threshold Cleared 
    IntelligentServerOverTemperatureWarningHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Over-Temperature Warning (Upper non-critical, going high)Cleared"
        --#SEVERITY INFORMATION
        ::= 65927
    IntelligentServerOverTemperatureWarningHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Over-Temperature Warning (Upper non-critical, going high)Cleared"
        --#SEVERITY INFORMATION
        ::= { IntelligentServerServerTRAPObject 65927 }
 
--  Temperature decreased below Upper critical threshold Cleared 
    IntelligentServerOverTemperatureCriticalLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Temperature problem (Upper critical, going low) Cleared"
        --#SEVERITY INFORMATION
        ::= 65928
    IntelligentServerOverTemperatureCriticalLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Temperature problem (Upper critical, going low) Cleared"
        --#SEVERITY INFORMATION
        ::= { IntelligentServerServerTRAPObject 65928 }
 
 -- Temperature increased above Upper critical threshold Cleared 
     IntelligentServerOverTemperatureCriticalHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Temperature problem (Upper critical, going high)Cleared"
        --#SEVERITY INFORMATION
        ::= 65929
    IntelligentServerOverTemperatureCriticalHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Temperature problem (Upper critical, going high)Cleared"
        --#SEVERITY INFORMATION
        ::= { IntelligentServerServerTRAPObject 65929 }
 
 -- Temperature decreased below Upper non-recoverable threshold Cleared 
     IntelligentServerOverTemperatureNonRecoverableLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Temperature problem (Upper non-recoverable, going low)Cleared"
        --#SEVERITY INFORMATION
        ::= 65930
    IntelligentServerOverTemperatureNonRecoverableLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Temperature problem (Upper non-recoverable, going low)Cleared"
        --#SEVERITY INFORMATION
        ::= { IntelligentServerServerTRAPObject 65930 }
 
 -- Temperature increased above Upper non-recoverable threshold Cleared 
     IntelligentServerOverTemperatureNonRecoverableHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Temperature problem (Upper non-recoverable, going high) Cleared"
        --#SEVERITY INFORMATION
        ::= 65931
    IntelligentServerOverTemperatureNonRecoverableHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Temperature problem (Upper non-recoverable, going high) Cleared"
        --#SEVERITY INFORMATION
        ::= { IntelligentServerServerTRAPObject 65931 }
       
 -- DTS Temperature Lower Non critical going low deasserted
    IntelligentServerDTSTemperatureLowerNonCriticalGoingLowDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Lower non-critical going low deasserted" 
        --#SEVERITY CRITICAL
        ::= 66000
    IntelligentServerDTSTemperatureLowerNonCriticalGoingLowDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Lower non-critical going low deasserted" 
        --#SEVERITY CRITICAL
        ::= { IntelligentServerServerTRAPObject 66000 }
 
 -- DTS Temperature Lower critical going low deasserted
    IntelligentServerDTSTemperatureLowerCriticalGoingLowDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Lower critical going low deasserted" 
        --#SEVERITY CRITICAL
        ::= 66002
    IntelligentServerDTSTemperatureLowerCriticalGoingLowDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Lower critical going low deasserted" 
        --#SEVERITY CRITICAL
        ::= { IntelligentServerServerTRAPObject 66002 }
 
--  Generic critical temperature problem 
    IntelligentServerGenericCriticalTemperature TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Generic Critical Temperature Problem (Transition to Critical from less severe)" 
        --#SEVERITY CRITICAL
        ::= 67330
    IntelligentServerGenericCriticalTemperature-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Generic Critical Temperature Problem (Transition to Critical from less severe)" 
        --#SEVERITY CRITICAL
        ::= { IntelligentServerServerTRAPObject 67330 }

--  Generic temperature warning 
    IntelligentServerGenericTemperatureWarning TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Generic Temperature Warning (Transition to Warning from less severe)"
        --#SEVERITY WARNING
        ::= 67331
    IntelligentServerGenericTemperatureWarning-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Generic Temperature Warning (Transition to Warning from less severe)"
        --#SEVERITY WARNING
        ::= { IntelligentServerServerTRAPObject 67331 }

-- **********************************************
-- *Voltage                                     *
-- **********************************************

--  Voltage has decreased below lower non-critical threshold        
    IntelligentServerUnderVoltageWarningLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Under-Voltage Warning (Lower non-critical, going low)"
        --#SEVERITY WARNING
        ::= 131328
    IntelligentServerUnderVoltageWarningLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Under-Voltage Warning (Lower non-critical, going low)"
        --#SEVERITY WARNING
        ::= { IntelligentServerServerTRAPObject 131328 }
 
-- Voltage has increased above lower non-critical threshold 
    IntelligentServerUnderVoltageWarningHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Under-Voltage Warning (Lower non-critical, going high)"
        --#SEVERITY WARNING
        ::= 131329
    IntelligentServerUnderVoltageWarningHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Under-Voltage Warning (Lower non-critical, going high)"
        --#SEVERITY WARNING
        ::= { IntelligentServerServerTRAPObject 131329 }
 
--  Voltage has decreased below lower critical threshold 
    IntelligentServerUnderVoltageCriticalLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Under-Voltage problem (Lower critical, going low)"
        --#SEVERITY CRITICAL
        ::= 131330
    IntelligentServerUnderVoltageCriticalLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Under-Voltage problem (Lower critical, going low)"
        --#SEVERITY CRITICAL
        ::= { IntelligentServerServerTRAPObject 131330 }
 
--  Voltage has increased above lower critical threshold 
    IntelligentServerUnderVoltageCriticalHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Under-Voltage problem (Lower critical, going high)" 
        --#SEVERITY CRITICAL
        ::= 131331
    IntelligentServerUnderVoltageCriticalHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Under-Voltage problem (Lower critical, going high)" 
        --#SEVERITY CRITICAL
        ::= { IntelligentServerServerTRAPObject 131331 }
 
--  Voltage has decreased below lower non-recoverable threshold 
    IntelligentServerUnderVoltageNonRecoverableLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Voltage problem (Lower non-recoverable, going low)" 
        --#SEVERITY CRITICAL
        ::= 131332
    IntelligentServerUnderVoltageNonRecoverableLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Voltage problem (Lower non-recoverable, going low)" 
        --#SEVERITY CRITICAL
        ::= { IntelligentServerServerTRAPObject 131332 }
 
--  Voltage has increased above lower non-recoverable threshold 
    IntelligentServerUnderVoltageNonRecoverableHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Under-Voltage problem (Lower non-recoverable, going high)" 
        --#SEVERITY CRITICAL
        ::= 131333
    IntelligentServerUnderVoltageNonRecoverableHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Under-Voltage problem (Lower non-recoverable, going high)" 
        --#SEVERITY CRITICAL
        ::= { IntelligentServerServerTRAPObject 131333 }
 
--  Voltage has decreased below Upper non-critical threshold 
    IntelligentServerOverVoltageWarningLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Over-Voltage Warning (Upper non-critical, going low)" 
        --#SEVERITY   WARNING
        ::= 131334
    IntelligentServerOverVoltageWarningLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Over-Voltage Warning (Upper non-critical, going low)" 
        --#SEVERITY   WARNING
        ::= { IntelligentServerServerTRAPObject 131334 }
 
--  Voltage has increased above upper non-critical threshold. 
    IntelligentServerOverVoltageWarningHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Over-Voltage Warning (Upper non-critical, going high)"
        --#SEVERITY WARNING
        ::= 131335
    IntelligentServerOverVoltageWarningHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Over-Voltage Warning (Upper non-critical, going high)"
        --#SEVERITY WARNING
        ::= { IntelligentServerServerTRAPObject 131335 }
 
--  Voltage has decreased below Upper critical threshold 
    IntelligentServerOverVoltageCriticalLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
        "Critical Over-Voltage problem (Upper critical, going low)"
        --#SEVERITY INFORMATION
        ::= 131336
    IntelligentServerOverVoltageCriticalLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
        "Critical Over-Voltage problem (Upper critical, going low)"
        --#SEVERITY INFORMATION
        ::= { IntelligentServerServerTRAPObject 131336 }
 
--  Voltage has increased above Upper critical threshold 
    IntelligentServerOverVoltageCriticalHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Voltage problem (Upper critical, going high)" 
        --#SEVERITY CRITICAL
        ::= 131337
    IntelligentServerOverVoltageCriticalHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Voltage problem (Upper critical, going high)" 
        --#SEVERITY CRITICAL
        ::= { IntelligentServerServerTRAPObject 131337 }
 
--  Voltage has decreased below Upper non-recoverable threshold 
    IntelligentServerOverVoltageNonRecoverableLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Voltage problem (Upper non-recoverable, going low)" 
        --#SEVERITY INFORMATION
        ::= 131338
    IntelligentServerOverVoltageNonRecoverableLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Voltage problem (Upper non-recoverable, going low)" 
        --#SEVERITY INFORMATION
        ::= { IntelligentServerServerTRAPObject 131338 }
 
 -- Voltage has increased above Upper non-recoverable threshold 
     IntelligentServerOverVoltageNonRecoverableHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Voltage problem (Upper non-recoverable, going high)"
        --#SEVERITY CRITICAL
        ::= 131339
    IntelligentServerOverVoltageNonRecoverableHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Voltage problem (Upper non-recoverable, going high)"
        --#SEVERITY CRITICAL
        ::= { IntelligentServerServerTRAPObject 131339 }
 
-- Voltage decreased below lower non-critical threshold Cleared 
    IntelligentServerUnderVoltageWarningLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Under-Voltage Warning (Lower non-critical, going low) Cleared" 
        --#SEVERITY INFORMATION
        ::= 131456
    IntelligentServerUnderVoltageWarningLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Under-Voltage Warning (Lower non-critical, going low) Cleared" 
        --#SEVERITY INFORMATION
        ::= { IntelligentServerServerTRAPObject 131456 }
 
-- Voltage increased above lower non-critical threshold Cleared 
    IntelligentServerUnderVoltageWarningHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Under-Voltage Warning (Lower non-critical, going high)Cleared" 
        --#SEVERITY INFORMATION
        ::= 131457
    IntelligentServerUnderVoltageWarningHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Under-Voltage Warning (Lower non-critical, going high)Cleared" 
        --#SEVERITY INFORMATION
        ::= { IntelligentServerServerTRAPObject 131457 }
 
--  Voltage decreased below lower critical threshold Cleared 
    IntelligentServerUnderVoltageCriticalLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Voltage problem (Lower critical, going low)Cleared" 
        --#SEVERITY INFORMATION
    ::= 131458
    IntelligentServerUnderVoltageCriticalLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Voltage problem (Lower critical, going low)Cleared" 
        --#SEVERITY INFORMATION
    ::= { IntelligentServerServerTRAPObject 131458 }
 
 -- Voltage increased above lower critical threshold Cleared 
     IntelligentServerUnderVoltageCriticalHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Voltage problem (Lower critical, going high) Cleared"
        --#SEVERITY INFORMATION
        ::= 131459
    IntelligentServerUnderVoltageCriticalHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Voltage problem (Lower critical, going high) Cleared"
        --#SEVERITY INFORMATION
        ::= { IntelligentServerServerTRAPObject 131459 }
 
--  Voltage decreased below lower non-recoverable threshold Cleared 
    IntelligentServerUnderVoltageNonRecoverableLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Voltage problem (Lower non-recoverable, going low)Cleared" 
        --#SEVERITY INFORMATION
        ::= 131460
    IntelligentServerUnderVoltageNonRecoverableLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Voltage problem (Lower non-recoverable, going low)Cleared" 
        --#SEVERITY INFORMATION
        ::= { IntelligentServerServerTRAPObject 131460 }
 
--  Voltage increased above lower non-recoverable threshold Cleared 
    IntelligentServerUnderVoltageNonRecoverableHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Under-Voltage problem (Lower non-recoverable, going high) Cleared" 
        --#SEVERITY INFORMATION
        ::= 131461
    IntelligentServerUnderVoltageNonRecoverableHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Under-Voltage problem (Lower non-recoverable, going high) Cleared" 
        --#SEVERITY INFORMATION
        ::= { IntelligentServerServerTRAPObject 131461 }
 
--  Voltage decreased below Upper non-critical threshold Cleared 
    IntelligentServerOverVoltageWarningLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Over-Voltage Warning (Upper non-critical, going low) Cleared" 
        --#SEVERITY INFORMATION
        ::= 131462
    IntelligentServerOverVoltageWarningLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Over-Voltage Warning (Upper non-critical, going low) Cleared" 
        --#SEVERITY INFORMATION
        ::= { IntelligentServerServerTRAPObject 131462 }
 
--  Voltage increased above upper non-critical threshold Cleared 
    IntelligentServerOverVoltageWarningHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Over-Voltage Warning (Upper non-critical, going high)Cleared" 
        --#SEVERITY INFORMATION
        ::= 131463
    IntelligentServerOverVoltageWarningHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Over-Voltage Warning (Upper non-critical, going high)Cleared" 
        --#SEVERITY INFORMATION
        ::= { IntelligentServerServerTRAPObject 131463 }
 
--  Voltage decreased below Upper critical threshold Cleared 
    IntelligentServerOverVoltageCriticalLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Voltage problem (Upper critical, going low) Cleared" 
        --#SEVERITY INFORMATION
        ::= 131464
    IntelligentServerOverVoltageCriticalLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Voltage problem (Upper critical, going low) Cleared" 
        --#SEVERITY INFORMATION
        ::= { IntelligentServerServerTRAPObject 131464 }
 
--  Voltage increased above Upper critical threshold Cleared 
    IntelligentServerOverVoltageCriticalHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Voltage problem (Upper critical, going high)Cleared" 
        --#SEVERITY INFORMATION
        ::= 131465
    IntelligentServerOverVoltageCriticalHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Voltage problem (Upper critical, going high)Cleared" 
        --#SEVERITY INFORMATION
        ::= { IntelligentServerServerTRAPObject 131465 }
 
--  Voltage decreased below Upper non-recoverable threshold Cleared 
    IntelligentServerOverVoltageNonRecoverableLowCleared TRAP-TYPE
    OBJECTS { altHostLocation, altTrapTime, altSysManufacture, altSysModel, altSensorName, altSensorType, altSensorReading, altSensorThreshold, altHostContact, altBMCHostName, altSysName, altSpTxtId, altPriority, altEventAssertOrDeassert }
    STATUS current
    ENTERPRISE IntelligentServerServerTRAPObject
    DESCRIPTION
        "Critical Over-Voltage problem (Upper non-recoverable, going low)Cleared"
        --#SEVERITY INFORMATION
    ::= 131466
    IntelligentServerOverVoltageNonRecoverableLowCleared-V2cV3 NOTIFICATION-TYPE
    OBJECTS { altHostLocation, altTrapTime, altSysManufacture, altSysModel, altSensorName, altSensorType, altSensorReading, altSensorThreshold, altHostContact, altBMCHostName, altSysName, altSpTxtId, altPriority, altEventAssertOrDeassert }
    STATUS current
    DESCRIPTION
        "Critical Over-Voltage problem (Upper non-recoverable, going low)Cleared"
        --#SEVERITY INFORMATION
    ::= { IntelligentServerServerTRAPObject 131466 }
 
--  Voltage increased above Upper non-recoverable threshold Cleared 
    IntelligentServerOverVoltageNonRecoverableHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
        "Critical Over-Voltage problem (Upper non-recoverable, going high) Cleared" 
        --#SEVERITY INFORMATION
        ::= 131467
    IntelligentServerOverVoltageNonRecoverableHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
        "Critical Over-Voltage problem (Upper non-recoverable, going high) Cleared" 
        --#SEVERITY INFORMATION
        ::= { IntelligentServerServerTRAPObject 131467 }
 
--  (Discrete voltage) Critical voltage problem 
    IntelligentServerGenericCriticalDiscreteVoltageCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Generic Critical Voltage Problem Cleared" 
        --#SEVERITY INFORMATION
        ::= 131840
    IntelligentServerGenericCriticalDiscreteVoltageCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Generic Critical Voltage Problem Cleared" 
        --#SEVERITY INFORMATION
        ::= { IntelligentServerServerTRAPObject 131840 }

--  (Discrete voltage) Critical voltage problem 
    IntelligentServerGenericCriticalDiscreteVoltage TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Generic Critical Voltage Problem (Transition to Critical from less severe)" 
        --#SEVERITY CRITICAL
        ::= 131841
    IntelligentServerGenericCriticalDiscreteVoltage-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Generic Critical Voltage Problem (Transition to Critical from less severe)" 
        --#SEVERITY CRITICAL
        ::= { IntelligentServerServerTRAPObject 131841 }
 
--  (Discrete voltage) Critical voltage problem cleared 
    IntelligentServerGenericCriticalDiscreteVoltage2Cleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Generic Critical Voltage Problem Cleared(Transition to OK)" 
        --#SEVERITY  INFORMATION
        ::= 132864
    IntelligentServerGenericCriticalDiscreteVoltage2Cleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Generic Critical Voltage Problem Cleared(Transition to OK)" 
        --#SEVERITY  INFORMATION
        ::= { IntelligentServerServerTRAPObject 132864 }
 
--  (Discrete voltage) Non-Critical voltage problem  
    IntelligentServerGenericNonCriticalDiscreteVoltage2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Generic Non-Critical Voltage Problem (Transition to Non-Critical from OK)" 
        --#SEVERITY  WARNING
        ::= 132865
    IntelligentServerGenericNonCriticalDiscreteVoltage2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Generic Non-Critical Voltage Problem (Transition to Non-Critical from OK)" 
        --#SEVERITY  WARNING
        ::= { IntelligentServerServerTRAPObject 132865 }
 
--  (Discrete voltage) Critical voltage problem 
    IntelligentServerGenericCriticalDiscreteVoltage2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Generic Critical Voltage Problem (Transition to Critical from less severe)"
        --#SEVERITY  CRITICAL
        ::= 132866
    IntelligentServerGenericCriticalDiscreteVoltage2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Generic Critical Voltage Problem (Transition to Critical from less severe)"
        --#SEVERITY  CRITICAL
        ::= { IntelligentServerServerTRAPObject 132866 }

--  (Discrete voltage) Non-Critical voltage problem 
    IntelligentServerGenericDiscreteVoltageWarning TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Generic Voltage Warning (Transition to Non-Critical from less severe)"
        --#SEVERITY  WARNING
        ::= 132867
    IntelligentServerGenericDiscreteVoltageWarning-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Generic Voltage Warning (Transition to Non-Critical from less severe)"
        --#SEVERITY  WARNING
        ::= { IntelligentServerServerTRAPObject 132867 }

--  (Discrete voltage) Non-Critical voltage problem 
    IntelligentServerGenericDiscreteVoltageWarning2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Generic Voltage Warning (Transition to Non-Critical from more severe)" 
        --#SEVERITY   WARNING
        ::= 132868
    IntelligentServerGenericDiscreteVoltageWarning2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Generic Voltage Warning (Transition to Non-Critical from more severe)" 
        --#SEVERITY   WARNING
        ::= { IntelligentServerServerTRAPObject 132868 }
 
--  (Discrete voltage) Non-Recoverable voltage problem 
    IntelligentServerGenericDiscreteVoltageNonRecoverable TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Generic Voltage Warning (Transition to Non-Recoverable)" 
        --#SEVERITY CRITICAL
        ::= 132869
    IntelligentServerGenericDiscreteVoltageNonRecoverable-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Generic Voltage Warning (Transition to Non-Recoverable)" 
        --#SEVERITY CRITICAL
        ::= { IntelligentServerServerTRAPObject 132869 }
 
--  (Discrete voltage) Non-Recoverable voltage problem 
    IntelligentServerGenericDiscreteVoltageMonitor TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Generic Discrete Voltage  (Monitor)"
        --#SEVERITY INFORMATION
        ::= 132870
    IntelligentServerGenericDiscreteVoltageMonitor-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Generic Discrete Voltage  (Monitor)"
        --#SEVERITY INFORMATION
        ::= { IntelligentServerServerTRAPObject 132870 }
 
--  (Discrete voltage) Non-Recoverable voltage problem 
    IntelligentServerGenericDiscreteVoltageInformational TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Generic Discrete Voltage  (Informational)" 
        --#SEVERITY INFORMATION
        ::= 132871
    IntelligentServerGenericDiscreteVoltageInformational-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Generic Discrete Voltage  (Informational)" 
        --#SEVERITY INFORMATION
        ::= { IntelligentServerServerTRAPObject 132871 }

-- **********************************************
-- *Current                                     * 
-- **********************************************

--  Current has decreased below lower non-critical threshold 
    IntelligentServerUnderCurrentWarningLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Under-Current Warning (Lower non-critical, going low)" 
        --#SEVERITY   WARNING
        ::= 196864
    IntelligentServerUnderCurrentWarningLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Under-Current Warning (Lower non-critical, going low)" 
        --#SEVERITY   WARNING
        ::= { IntelligentServerServerTRAPObject 196864 }
 
--  Current has increased above lower non-critical threshold 
    IntelligentServerUnderCurrentWarningHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Under-Current Warning (Lower non-critical, going high)" 
        --#SEVERITY   WARNING
        ::= 196865
    IntelligentServerUnderCurrentWarningHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Under-Current Warning (Lower non-critical, going high)" 
        --#SEVERITY   WARNING
        ::= { IntelligentServerServerTRAPObject 196865 }
 
--  Current has decreased below lower critical threshold 
    IntelligentServerUnderCurrentCriticalLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Current problem (Lower critical, going low)" 
        --#SEVERITY CRITICAL
        ::= 196866
    IntelligentServerUnderCurrentCriticalLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Current problem (Lower critical, going low)" 
        --#SEVERITY CRITICAL
        ::= { IntelligentServerServerTRAPObject 196866 }
 
--  Current has increased above lower critical threshold 
    IntelligentServerUnderCurrentCriticalHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Current problem (Lower critical, going high)" 
        --#SEVERITY CRITICAL
        ::= 196867
    IntelligentServerUnderCurrentCriticalHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Current problem (Lower critical, going high)" 
        --#SEVERITY CRITICAL
        ::= { IntelligentServerServerTRAPObject 196867 }
 
--  Current has decreased below lower non-recoverable threshold 
    IntelligentServerUnderCurrentNonRecoverableLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Current problem (Lower non-recoverable, going low)" 
        --#SEVERITY CRITICAL
        ::= 196868
    IntelligentServerUnderCurrentNonRecoverableLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Current problem (Lower non-recoverable, going low)" 
        --#SEVERITY CRITICAL
        ::= { IntelligentServerServerTRAPObject 196868 }
 
--  Current has increased above lower non-recoverable threshold 
    IntelligentServerUnderCurrentNonRecoverableHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Under-Current problem (Lower non-recoverable, going high)" 
        --#SEVERITY CRITICAL
        ::= 196869
    IntelligentServerUnderCurrentNonRecoverableHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Under-Current problem (Lower non-recoverable, going high)" 
        --#SEVERITY CRITICAL
        ::= { IntelligentServerServerTRAPObject 196869 }
 
--  Current has decreased below Upper non-critical threshold 
    IntelligentServerOverCurrentWarningLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Over-Current Warning (Upper non-critical, going low)" 
        --#SEVERITY   INFORMATION
        ::= 196870
    IntelligentServerOverCurrentWarningLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Over-Current Warning (Upper non-critical, going low)" 
        --#SEVERITY   INFORMATION
        ::= { IntelligentServerServerTRAPObject 196870 }
 
--  Current has increased above upper non-critical threshold. 
    IntelligentServerOverCurrentWarningHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Over-Current Warning (Upper non-critical, going high)" 
        --#SEVERITY   WARNING
        ::= 196871
    IntelligentServerOverCurrentWarningHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Over-Current Warning (Upper non-critical, going high)" 
        --#SEVERITY   WARNING
        ::= { IntelligentServerServerTRAPObject 196871 }
 
-- Current has decreased below Upper critical threshold 
    IntelligentServerOverCurrentCriticalLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Current problem (Upper critical, going low)" 
        --#SEVERITY INFORMATION
        ::= 196872
    IntelligentServerOverCurrentCriticalLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Current problem (Upper critical, going low)" 
        --#SEVERITY INFORMATION
        ::= { IntelligentServerServerTRAPObject 196872 }
 
--  Current has increased above Upper critical threshold 
    IntelligentServerOverCurrentCriticalHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Current problem (Upper critical, going high)"
        --#SEVERITY CRITICAL
        ::= 196873
    IntelligentServerOverCurrentCriticalHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Current problem (Upper critical, going high)"
        --#SEVERITY CRITICAL
        ::= { IntelligentServerServerTRAPObject 196873 }
 
--  Current has decreased below Upper non-recoverable threshold 
    IntelligentServerOverCurrentNonRecoverableLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Current problem (Upper non-recoverable, going low)" 
        --#SEVERITY CRITICAL
        ::= 196874
    IntelligentServerOverCurrentNonRecoverableLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Current problem (Upper non-recoverable, going low)" 
        --#SEVERITY CRITICAL
        ::= { IntelligentServerServerTRAPObject 196874 }
 
--  Current has increased above Upper non-recoverable threshold 
    IntelligentServerOverCurrentNonRecoverableHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Current problem (Upper non-recoverable, going high)" 
        --#SEVERITY CRITICAL
        ::= 196875
    IntelligentServerOverCurrentNonRecoverableHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Current problem (Upper non-recoverable, going high)" 
        --#SEVERITY CRITICAL
        ::= { IntelligentServerServerTRAPObject 196875 }
 
--  Current decreased below lower non-critical threshold Cleared 
    IntelligentServerUnderCurrentWarningLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Under-Current Warning (Lower non-critical, going low) Cleared"
        --#SEVERITY INFORMATION
        ::= 196992
    IntelligentServerUnderCurrentWarningLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Under-Current Warning (Lower non-critical, going low) Cleared"
        --#SEVERITY INFORMATION
        ::= { IntelligentServerServerTRAPObject 196992 }
 
-- Current increased above lower non-critical threshold Cleared 
    IntelligentServerUnderCurrentWarningHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Under-Current Warning (Lower non-critical, going high)Cleared" 
        --#SEVERITY INFORMATION
        ::= 196993
    IntelligentServerUnderCurrentWarningHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Under-Current Warning (Lower non-critical, going high)Cleared" 
        --#SEVERITY INFORMATION
        ::= { IntelligentServerServerTRAPObject 196993 }
 
-- Current decreased below lower critical threshold Cleared 
    IntelligentServerUnderCurrentCriticalLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Current problem (Lower critical, going low)Cleared" 
        --#SEVERITY INFORMATION
        ::= 196994
    IntelligentServerUnderCurrentCriticalLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Current problem (Lower critical, going low)Cleared" 
        --#SEVERITY INFORMATION
        ::= { IntelligentServerServerTRAPObject 196994 }
 
--  Current increased above lower critical threshold Cleared 
    IntelligentServerUnderCurrentCriticalHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Current problem (Lower critical, going high) Cleared" 
        --#SEVERITY INFORMATION
        ::= 196995
    IntelligentServerUnderCurrentCriticalHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Current problem (Lower critical, going high) Cleared" 
        --#SEVERITY INFORMATION
        ::= { IntelligentServerServerTRAPObject 196995 }
 
--  Current decreased below lower non-recoverable threshold Cleared 
    IntelligentServerUnderCurrentNonRecoverableLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Current problem (Lower non-recoverable, going low)Cleared"
        --#SEVERITY INFORMATION
        ::= 196996
    IntelligentServerUnderCurrentNonRecoverableLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Current problem (Lower non-recoverable, going low)Cleared"
        --#SEVERITY INFORMATION
        ::= { IntelligentServerServerTRAPObject 196996 }
 
--  Current increased above lower non-recoverable threshold Cleared 
    IntelligentServerUnderCurrentNonRecoverableHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Under-Current problem (Lower non-recoverable, going high) Cleared" 
        --#SEVERITY INFORMATION
        ::= 196997
    IntelligentServerUnderCurrentNonRecoverableHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Under-Current problem (Lower non-recoverable, going high) Cleared" 
        --#SEVERITY INFORMATION
        ::= { IntelligentServerServerTRAPObject 196997 }
 
--  Current decreased below Upper non-critical threshold Cleared 
    IntelligentServerOverCurrentWarningLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Over-Current Warning (Upper non-critical, going low) Cleared" 
        --#SEVERITY INFORMATION
        ::= 196998
    IntelligentServerOverCurrentWarningLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Over-Current Warning (Upper non-critical, going low) Cleared" 
        --#SEVERITY INFORMATION
        ::= { IntelligentServerServerTRAPObject 196998 }
 
--  Current increased above upper non-critical threshold Cleared 
    IntelligentServerOverCurrentWarningHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Over-Current Warning (Upper non-critical, going high)Cleared" 
        --#SEVERITY INFORMATION
        ::= 196999
    IntelligentServerOverCurrentWarningHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Over-Current Warning (Upper non-critical, going high)Cleared" 
        --#SEVERITY INFORMATION
        ::= { IntelligentServerServerTRAPObject 196999 }
 
-- Current decreased below Upper critical threshold Cleared 
    IntelligentServerOverCurrentCriticalLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Current problem (Upper critical, going low) Cleared" 
        --#SEVERITY INFORMATION
        ::= 197000
    IntelligentServerOverCurrentCriticalLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Current problem (Upper critical, going low) Cleared" 
        --#SEVERITY INFORMATION
        ::= { IntelligentServerServerTRAPObject 197000 }
 
 -- Current increased above Upper critical threshold Cleared 
     IntelligentServerOverCurrentCriticalHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Current problem (Upper critical, going high)Cleared"
        --#SEVERITY INFORMATION
        ::= 197001
    IntelligentServerOverCurrentCriticalHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Current problem (Upper critical, going high)Cleared"
        --#SEVERITY INFORMATION
        ::= { IntelligentServerServerTRAPObject 197001 }
 
-- Current decreased below Upper non-recoverable threshold Cleared 
    IntelligentServerOverCurrentNonRecoverableLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Over-Current problem (Upper non-recoverable, going low)Cleared" 
        --#SEVERITY INFORMATION
        ::= 197002
    IntelligentServerOverCurrentNonRecoverableLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Over-Current problem (Upper non-recoverable, going low)Cleared" 
        --#SEVERITY INFORMATION
        ::= { IntelligentServerServerTRAPObject 197002 }
 
-- Current increased above Upper non-recoverable threshold Cleared 
    IntelligentServerOverCurrentNonRecoverableHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Over-Current problem (Upper non-recoverable, going high) Cleared" 
        --#SEVERITY INFORMATION
        ::= 197003
    IntelligentServerOverCurrentNonRecoverableHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Over-Current problem (Upper non-recoverable, going high) Cleared" 
        --#SEVERITY INFORMATION
        ::= { IntelligentServerServerTRAPObject 197003 }
 
 
-- ********************************************** 
-- *        Fan         * 
-- ********************************************** 

-- Fan speed has decreased below lower non-critical threshold 
    IntelligentServerFanUnderSpeedWarningLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Under Speed Warning (Lower non-critical, going low)" 
        --#SEVERITY  WARNING
        ::= 262400
    IntelligentServerFanUnderSpeedWarningLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Under Speed Warning (Lower non-critical, going low)" 
        --#SEVERITY  WARNING
        ::= { IntelligentServerServerTRAPObject 262400 }
 
-- Fan speed has increased above lower non-critical threshold 
    IntelligentServerFanUnderSpeedWarningHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Under Speed Warning (Lower non-critical, going high)"
        --#SEVERITY  INFORMATION
        ::= 262401
    IntelligentServerFanUnderSpeedWarningHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Under Speed Warning (Lower non-critical, going high)"
        --#SEVERITY  INFORMATION
        ::= { IntelligentServerServerTRAPObject 262401 }
 
-- Fan speed has decreased below lower critical threshold 
    IntelligentServerFanUnderSpeedCriticalLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Fan Under Speed problem (Lower critical, going low)" 
        --#SEVERITY  CRITICAL
        ::= 262402
    IntelligentServerFanUnderSpeedCriticalLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Fan Under Speed problem (Lower critical, going low)" 
        --#SEVERITY  CRITICAL
        ::= { IntelligentServerServerTRAPObject 262402 }
 
 -- Fan speed has increased above lower critical threshold 
     IntelligentServerFanUnderSpeedCriticalHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Fan Under Speed problem (Lower critical, going high)" 
        --#SEVERITY INFORMATION
        ::= 262403
    IntelligentServerFanUnderSpeedCriticalHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Fan Under Speed problem (Lower critical, going high)" 
        --#SEVERITY INFORMATION
        ::= { IntelligentServerServerTRAPObject 262403 }
     
 -- Fan speed has decreased below lower non-recoverable threshold 
     IntelligentServerFanUnderSpeedNonRecoverableLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Fan Under Speed problem (Lower non-recoverable, going low)" 
        --#SEVERITY CRITICAL
        ::= 262404
    IntelligentServerFanUnderSpeedNonRecoverableLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Fan Under Speed problem (Lower non-recoverable, going low)" 
        --#SEVERITY CRITICAL
        ::= { IntelligentServerServerTRAPObject 262404 }
 
 -- Fan speed has increased above lower non-recoverable threshold 
     IntelligentServerFanUnderSpeedNonRecoverableHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Fan Under Speed problem (Lower non-recoverable, going high)" 
        --#SEVERITY INFORMATION
        ::= 262405
    IntelligentServerFanUnderSpeedNonRecoverableHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Fan Under Speed problem (Lower non-recoverable, going high)" 
        --#SEVERITY INFORMATION
        ::= { IntelligentServerServerTRAPObject 262405 }

-- Fan speed has decreased below Upper non-critical threshold 
    IntelligentServerFanOverSpeedWarningLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Over Speed Warning (Upper non-critical, going low)" 
        --#SEVERITY INFORMATION
        ::= 262406
    IntelligentServerFanOverSpeedWarningLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Over Speed Warning (Upper non-critical, going low)" 
        --#SEVERITY INFORMATION
        ::= { IntelligentServerServerTRAPObject 262406 }
 
-- Fan speed has increased above upper non-critical threshold. 
    IntelligentServerFanOverSpeedWarningHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Over Speed Warning (Upper non-critical, going high)" 
        --#SEVERITY   WARNING
        ::= 262407
    IntelligentServerFanOverSpeedWarningHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Over Speed Warning (Upper non-critical, going high)" 
        --#SEVERITY   WARNING
        ::= { IntelligentServerServerTRAPObject 262407 }
 
-- Fan speed has decreased below Upper critical threshold 
    IntelligentServerFanOverSpeedCriticalLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Fan Over Speed problem (Upper critical, going low)" 
        --#SEVERITY INFORMATION
        ::= 262408
    IntelligentServerFanOverSpeedCriticalLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Fan Over Speed problem (Upper critical, going low)" 
        --#SEVERITY INFORMATION
        ::= { IntelligentServerServerTRAPObject 262408 }
 
 -- Fan speed has increased above Upper critical threshold 
     IntelligentServerFanOverSpeedCriticalHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Fan Over Speed problem (Upper critical, going high)" 
        --#SEVERITY CRITICAL
        ::= 262409
    IntelligentServerFanOverSpeedCriticalHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Fan Over Speed problem (Upper critical, going high)" 
        --#SEVERITY CRITICAL
        ::= { IntelligentServerServerTRAPObject 262409 }
 
 -- Fan speed has decreased below Upper non-recoverable threshold 
     IntelligentServerFanOverSpeedNonRecoverableLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Fan Over Speed problem (Upper non-recoverable, going low)" 
        --#SEVERITY INFORMATION
        ::= 262410
    IntelligentServerFanOverSpeedNonRecoverableLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Fan Over Speed problem (Upper non-recoverable, going low)" 
        --#SEVERITY INFORMATION
        ::= { IntelligentServerServerTRAPObject 262410 }
 
 -- Fan speed has increased above Upper non-recoverable threshold 
     IntelligentServerFanOverSpeedNonRecoverableHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Fan Over Speed problem (Upper non-recoverable, going high)" 
        --#SEVERITY CRITICAL
        ::= 262411
    IntelligentServerFanOverSpeedNonRecoverableHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Fan Over Speed problem (Upper non-recoverable, going high)" 
        --#SEVERITY CRITICAL
        ::= { IntelligentServerServerTRAPObject 262411 }
 
-- Fan speed has increased above Upper non-recoverable threshold 
    IntelligentServerWxlTest TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "IntelligentServer Snmp test"
        --#SEVERITY INFORMATION 
        ::= 262412
    IntelligentServerWxlTest-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "IntelligentServer Snmp test"
        --#SEVERITY INFORMATION 
        ::= { IntelligentServerServerTRAPObject 262412 }
 
-- Fan speed decreased below lower non-critical threshold Cleared 
    IntelligentServerFanUnderSpeedWarningLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Under Speed Warning (Lower non-critical, going low) Cleared" 
        --#SEVERITY INFORMATION
        ::= 262528
    IntelligentServerFanUnderSpeedWarningLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Under Speed Warning (Lower non-critical, going low) Cleared" 
        --#SEVERITY INFORMATION
        ::= { IntelligentServerServerTRAPObject 262528 }
 
-- Fan speed increased above lower non-critical threshold Cleared 
    IntelligentServerFanUnderSpeedWarningHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Under Speed Warning (Lower non-critical, going high)Cleared" 
        --#SEVERITY INFORMATION
        ::= 262529
    IntelligentServerFanUnderSpeedWarningHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Under Speed Warning (Lower non-critical, going high)Cleared" 
        --#SEVERITY INFORMATION
        ::= { IntelligentServerServerTRAPObject 262529 }
 
-- Fan speed decreased below lower critical threshold Cleared 
    IntelligentServerFanUnderSpeedCriticalLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Fan Under Speed problem (Lower critical, going low)Cleared" 
        --#SEVERITY INFORMATION
        ::= 262530
    IntelligentServerFanUnderSpeedCriticalLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Fan Under Speed problem (Lower critical, going low)Cleared" 
        --#SEVERITY INFORMATION
        ::= { IntelligentServerServerTRAPObject 262530 }
 
 -- Fan speed increased above lower critical threshold Cleared 
     IntelligentServerFanUnderSpeedCriticalHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Fan Under Speed problem (Lower critical, going high) Cleared" 
        --#SEVERITY INFORMATION
        ::= 262531
    IntelligentServerFanUnderSpeedCriticalHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Fan Under Speed problem (Lower critical, going high) Cleared" 
        --#SEVERITY INFORMATION
        ::= { IntelligentServerServerTRAPObject 262531 }
 
 -- Fan speed decreased below lower non-recoverable threshold Cleared 
     IntelligentServerFanUnderSpeedNonRecoverableLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Fan Under Speed problem (Lower non-recoverable, going low)Cleared" 
        --#SEVERITY INFORMATION
        ::= 262532
    IntelligentServerFanUnderSpeedNonRecoverableLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Fan Under Speed problem (Lower non-recoverable, going low)Cleared" 
        --#SEVERITY INFORMATION
        ::= { IntelligentServerServerTRAPObject 262532 }
     
 -- Fan speed increased above lower non-recoverable threshold Cleared 
     IntelligentServerFanUnderSpeedNonRecoverableHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Fan Under Speed problem (Lower non-recoverable, going high) Cleared" 
        --#SEVERITY INFORMATION
        ::= 262533
    IntelligentServerFanUnderSpeedNonRecoverableHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Fan Under Speed problem (Lower non-recoverable, going high) Cleared" 
        --#SEVERITY INFORMATION
        ::= { IntelligentServerServerTRAPObject 262533 }
 
-- Fan speed decreased below Upper non-critical threshold Cleared 
    IntelligentServerFanOverSpeedWarningLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Over Speed Warning (Upper non-critical, going low) Cleared"
        --#SEVERITY INFORMATION
        ::= 262534
    IntelligentServerFanOverSpeedWarningLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Over Speed Warning (Upper non-critical, going low) Cleared"
        --#SEVERITY INFORMATION
        ::= { IntelligentServerServerTRAPObject 262534 }
 
-- Fan speed increased above upper non-critical threshold Cleared 
    IntelligentServerFanOverSpeedWarningHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Over Speed Warning (Upper non-critical, going high)Cleared" 
        --#SEVERITY INFORMATION
        ::= 262535
    IntelligentServerFanOverSpeedWarningHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Over Speed Warning (Upper non-critical, going high)Cleared" 
        --#SEVERITY INFORMATION
        ::= { IntelligentServerServerTRAPObject 262535 }
 
-- Fan speed decreased below Upper critical threshold Cleared 
    IntelligentServerFanOverSpeedCriticalLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Fan Over Speed problem (Upper critical, going low) Cleared" 
        --#SEVERITY INFORMATION
        ::= 262536
    IntelligentServerFanOverSpeedCriticalLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Fan Over Speed problem (Upper critical, going low) Cleared" 
        --#SEVERITY INFORMATION
        ::= { IntelligentServerServerTRAPObject 262536 }
 
 -- Fan speed increased above Upper critical threshold Cleared 
     IntelligentServerFanOverSpeedCriticalHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Fan Over Speed problem (Upper critical, going high)Cleared" 
        --#SEVERITY INFORMATION
        ::= 262537
    IntelligentServerFanOverSpeedCriticalHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Fan Over Speed problem (Upper critical, going high)Cleared" 
        --#SEVERITY INFORMATION
        ::= { IntelligentServerServerTRAPObject 262537 }
 
 -- Fan speed decreased below Upper non-recoverable threshold Cleared 
     IntelligentServerFanOverSpeedNonRecoverableLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Fan Over Speed problem (Upper non-recoverable, going low)Cleared" 
        --#SEVERITY INFORMATION
        ::= 262538
    IntelligentServerFanOverSpeedNonRecoverableLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Fan Over Speed problem (Upper non-recoverable, going low)Cleared" 
        --#SEVERITY INFORMATION
        ::= { IntelligentServerServerTRAPObject 262538 }
 
 -- Fan speed increased above Upper non-recoverable threshold Cleared 
     IntelligentServerFanOverSpeedNonRecoverableHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Fan Over Speed problem (Upper non-recoverable, going high) Cleared" 
        --#SEVERITY INFORMATION
        ::= 262539
    IntelligentServerFanOverSpeedNonRecoverableHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Fan Over Speed problem (Upper non-recoverable, going high) Cleared" 
        --#SEVERITY INFORMATION
        ::= { IntelligentServerServerTRAPObject 262539 }
        
-- Fan Status Transition to Non-Critical from OK Assert
    IntelligentServerFanStatusTransitionToNonCriticalFromOKAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Status Transition to Non-Critical from OK Assert"
        --#SEVERITY CRITICAL
        ::= 263937
    IntelligentServerFanStatusTransitionToNonCriticalFromOKAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Status Transition to Non-Critical from OK Assert"
        --#SEVERITY CRITICAL
        ::= { IntelligentServerServerTRAPObject 263937 }

-- Fan Status Transition to Non-Critical from OK Deassert
    IntelligentServerFanStatusTransitionToNonCriticalFromOKDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Status Transition to Non-Critical from OK Deassert"
        --#SEVERITY CRITICAL
        ::= 264065
    IntelligentServerFanStatusTransitionToNonCriticalFromOKDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Status Transition to Non-Critical from OK Deassert"
        --#SEVERITY CRITICAL
        ::= { IntelligentServerServerTRAPObject 264065 }

-- Fan Present Device Inserted/Device Present-asserted
    IntelligentServerFanPresentAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Present Device Inserted/Device Present Assert"
        --#SEVERITY CRITICAL
        ::= 264193
    IntelligentServerFanPresentAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Present Device Inserted/Device Present Assert"
        --#SEVERITY CRITICAL
        ::= { IntelligentServerServerTRAPObject 264193 }

-- Fan Present Device Inserted/Device Present-deasserted
    IntelligentServerFanPresentDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Present Device Inserted/Device Present Deassert"
        --#SEVERITY CRITICAL
        ::= 264321
    IntelligentServerFanPresentDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Present Device Inserted/Device Present Deassert"
        --#SEVERITY CRITICAL
        ::= { IntelligentServerServerTRAPObject 264321 }
        
-- Power Capacity Transition to Non-Critical from OK Assert
    IntelligentServerPowerCapacityTransitionToNonCriticalFromOKAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Capacity Transition to Non-Critical from OK Assert"
        --#SEVERITY CRITICAL
        ::= 1181441
    IntelligentServerPowerCapacityTransitionToNonCriticalFromOKAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Capacity Transition to Non-Critical from OK Assert"
        --#SEVERITY CRITICAL
        ::= { IntelligentServerServerTRAPObject 1181441 }
-- Power Capacity Transition to Non-Critical from OK Deassert
    IntelligentServerPowerCapacityTransitionToNonCriticalFromOKDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Capacity Transition to Non-Critical from OK Deassert"
        --#SEVERITY CRITICAL
        ::= 1181569
    IntelligentServerPowerCapacityTransitionToNonCriticalFromOKDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Capacity Transition to Non-Critical from OK Deassert"
        --#SEVERITY CRITICAL
        ::= { IntelligentServerServerTRAPObject 1181569 }
 
 -- Fan Removed/Absent 
     IntelligentServerFanRemoved TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Fan Removed/Absent"
        --#SEVERITY CRITICAL
        ::= 264192
    IntelligentServerFanRemoved-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Fan Removed/Absent"
        --#SEVERITY CRITICAL
        ::= { IntelligentServerServerTRAPObject 264192 }

-- Fan Removed/Absent 
      IntelligentServerFanAbsent TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Removed/Absent" 
        --#SEVERITY INFORMATION
        ::= 264320
    IntelligentServerFanAbsent-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Removed/Absent" 
        --#SEVERITY INFORMATION
        ::= { IntelligentServerServerTRAPObject 264320 }
 
-- Fan Full Redundancy  
    IntelligentServerFanFullRedundancy TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Fan redundancy has returned to Normal"
        --#SEVERITY INFORMATION
        ::= 264960
    IntelligentServerFanFullRedundancy-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Fan redundancy has returned to Normal"
        --#SEVERITY INFORMATION
        ::= { IntelligentServerServerTRAPObject 264960 }

-- Fan Redundancy lost Assert
    IntelligentServerFanRedundancyLostAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Redundancy has been Lost Assert"
        --#SEVERITY CRITICAL
        ::= 264961
    IntelligentServerFanRedundancyLostAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Redundancy has been Lost Assert"
        --#SEVERITY CRITICAL
        ::= { IntelligentServerServerTRAPObject 264961 }

-- Fan Redundancy degraded 
    IntelligentServerFanRedundancyDegraded TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Redundancy is in a degraded state"
        --#SEVERITY   WARNING
        ::= 264962
    IntelligentServerFanRedundancyDegraded-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Redundancy is in a degraded state"
        --#SEVERITY   WARNING
        ::= { IntelligentServerServerTRAPObject 264962 }
        
-- Fan Redundancy lost Deassert
    IntelligentServerFanRedundancyLostDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Fan Redundancy has been Lost Deassert"
        --#SEVERITY CRITICAL
        ::= 265089
    IntelligentServerFanRedundancyLostDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Fan Redundancy has been Lost Deassert"
        --#SEVERITY CRITICAL
        ::= { IntelligentServerServerTRAPObject 265089 }

-- **********************************************
--* Chassis Intrusion                          *
-- **********************************************

--Chassis Intrusion 
    IntelligentServerChassisIntrusion TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis Intrusion - Physical Security Violation"
        --#SEVERITY CRITICAL
        ::= 356096
    IntelligentServerChassisIntrusion-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis Intrusion - Physical Security Violation"
        --#SEVERITY CRITICAL
        ::= { IntelligentServerServerTRAPObject 356096 }

--Chassis Drive Bay Intrusion 
    IntelligentServerChassisDriveBayIntrusion TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Chassis Intrusion - Drive Bay Violation"
        --#SEVERITY CRITICAL
        ::= 356097
    IntelligentServerChassisDriveBayIntrusion-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Chassis Intrusion - Drive Bay Violation"
        --#SEVERITY CRITICAL
        ::= { IntelligentServerServerTRAPObject 356097 }
 
 -- I/O Card Area Intrusion 
     IntelligentServerChassisIOCardAreaIntrusion TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "I/O Card Area Intrusion" 
        --#SEVERITY CRITICAL
        ::= 356098
    IntelligentServerChassisIOCardAreaIntrusion-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "I/O Card Area Intrusion" 
        --#SEVERITY CRITICAL
        ::= { IntelligentServerServerTRAPObject 356098 }
 
 -- Processor Area Intrusion 
     IntelligentServerChassisProcessorAreaIntrusion TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        --#SEVERITY CRITICAL
        DESCRIPTION
            "Processor Area Intrusion" 
        ::= 356099
    IntelligentServerChassisProcessorAreaIntrusion-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        --#SEVERITY CRITICAL
        DESCRIPTION
            "Processor Area Intrusion" 
        ::= { IntelligentServerServerTRAPObject 356099 }
 
-- LAN Leash Lost 
    IntelligentServerChassisLANLeashLost TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        --#SEVERITY CRITICAL
        DESCRIPTION
            "LAN Leash Lost" 
        ::= 356100
    IntelligentServerChassisLANLeashLost-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
	    --#SEVERITY CRITICAL
        DESCRIPTION
            "LAN Leash Lost" 
        ::= { IntelligentServerServerTRAPObject 356100 }
 
-- Unauthorized dock 
    IntelligentServerChassisUnauthorizedDock TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        --#SEVERITY CRITICAL
        DESCRIPTION
            "Unauthorized dock"
        ::= 356101
    IntelligentServerChassisUnauthorizedDock-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
	    --#SEVERITY CRITICAL
        DESCRIPTION
            "Unauthorized dock"
        ::= { IntelligentServerServerTRAPObject 356101 }
 
-- Fan Area Intrusion 
    IntelligentServerChassisFanAreaIntrusion TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
        --#SEVERITY CRITICAL
            "Fan Area Intrusion" 
        ::= 356102
    IntelligentServerChassisFanAreaIntrusion-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
	    --#SEVERITY CRITICAL
            "Fan Area Intrusion" 
        ::= { IntelligentServerServerTRAPObject 356102 }
               
-- Cooling Liquid Leakage Power off
    IntelligentServerCoolingLiquidLeakagePoweroff TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
        --#SEVERITY CRITICAL
            "Cooling Liquid Leakage & Power off" 
        ::= 356103
    IntelligentServerCoolingLiquidLeakagePoweroff-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
	    --#SEVERITY CRITICAL
            "Cooling Liquid Leakage & Power off" 
        ::= { IntelligentServerServerTRAPObject 356103 }
                
-- Cooling Liquid Leakage Line self-test faild
    IntelligentServerCoolingLiquidLeakageLineselftestfaild TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
        --#SEVERITY CRITICAL
            "Cooling Liquid Leakage Line self-test faild" 
        ::= 356104
    IntelligentServerCoolingLiquidLeakageLineselftestfaild-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
	    --#SEVERITY CRITICAL
            "Cooling Liquid Leakage Line self-test faild" 
        ::= { IntelligentServerServerTRAPObject 356104 }
 
-- Chassis Intrusion cleared 
    IntelligentServerChassisIntrusionCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis Intrusion (Physical Security Violation) Event Cleared" 
            --#SEVERITY INFORMATION
        ::= 356224
    IntelligentServerChassisIntrusionCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis Intrusion (Physical Security Violation) Event Cleared" 
	        --#SEVERITY INFORMATION
        ::= { IntelligentServerServerTRAPObject 356224 }

-- Chassis Drive Bay Intrusion Cleared 
    IntelligentServerChassisDriveBayIntrusionCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis Intrusion - Drive Bay Violation Cleared" 
            --#SEVERITY INFORMATION
        ::= 356225
    IntelligentServerChassisDriveBayIntrusionCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis Intrusion - Drive Bay Violation Cleared" 
	        --#SEVERITY INFORMATION
        ::= { IntelligentServerServerTRAPObject 356225 }
 
-- I/O Card Area Intrusion Cleared 
    IntelligentServerChassisIOCardAreaIntrusionCleared TRAP-TYPE
    OBJECTS { altHostLocation, altTrapTime, altSysManufacture, altSysModel, altSensorName, altSensorType, altSensorReading, altSensorThreshold, altHostContact, altBMCHostName, altSysName, altSpTxtId, altPriority, altEventAssertOrDeassert }
    STATUS current
    ENTERPRISE IntelligentServerServerTRAPObject
    DESCRIPTION
        "I/O Card Area Intrusion Cleared" 
            --#SEVERITY INFORMATION
    ::= 356226
    IntelligentServerChassisIOCardAreaIntrusionCleared-V2cV3 NOTIFICATION-TYPE
    OBJECTS { altHostLocation, altTrapTime, altSysManufacture, altSysModel, altSensorName, altSensorType, altSensorReading, altSensorThreshold, altHostContact, altBMCHostName, altSysName, altSpTxtId, altPriority, altEventAssertOrDeassert }
    STATUS current
    DESCRIPTION
        "I/O Card Area Intrusion Cleared" 
            --#SEVERITY INFORMATION
    ::= { IntelligentServerServerTRAPObject 356226 }
 
-- Processor Area Intrusion Cleared 
    IntelligentServerChassisProcessorAreaIntrusionCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Area Intrusion Cleared" 
        --#SEVERITY INFORMATION
        ::= 356227
    IntelligentServerChassisProcessorAreaIntrusionCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Area Intrusion Cleared" 
        --#SEVERITY INFORMATION
        ::= { IntelligentServerServerTRAPObject 356227 }
 
-- LAN Leash Lost Cleared 
    IntelligentServerChassisLANLeashLostCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "LAN Leash Lost" 
        --#SEVERITY INFORMATION
        ::= 356228
    IntelligentServerChassisLANLeashLostCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "LAN Leash Lost" 
        --#SEVERITY INFORMATION
        ::= { IntelligentServerServerTRAPObject 356228 }
 
-- Unauthorized dock Cleared 
    IntelligentServerChassisUnauthorizedDockCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Unauthorized dock Cleared" 
        --#SEVERITY INFORMATION
    ::= 356229
    IntelligentServerChassisUnauthorizedDockCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Unauthorized dock Cleared" 
        --#SEVERITY INFORMATION
    ::= { IntelligentServerServerTRAPObject 356229 }
 
-- Fan Area Intrusion Cleared 
    IntelligentServerChassisFanAreaIntrusionCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Fan Area Intrusion Cleared" 
        --#SEVERITY INFORMATION
        ::= 356230
    IntelligentServerChassisFanAreaIntrusionCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Fan Area Intrusion Cleared" 
        --#SEVERITY INFORMATION
        ::= { IntelligentServerServerTRAPObject 356230 }


 -- Processor Upper Hdd Drawer Intrusion 
     IntelligentServerUpperHddDrawerIntrusion TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        --#SEVERITY INFO
        DESCRIPTION
            "Upper Hdd Drawer Intrusion" 
        ::= 356105
    IntelligentServerUpperHddDrawerIntrusion-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        --#SEVERITY INFO
        DESCRIPTION
            "Upper Hdd Drawer Intrusion" 
        ::= { IntelligentServerServerTRAPObject 356105 }
        
-- Processor Upper Hdd Drawer Intrusion Cleared 
    IntelligentServerUpperHddDrawerIntrusionCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Upper Hdd Drawer Intrusion Cleared" 
        --#SEVERITY INFORMATION
        ::= 356233
    IntelligentServerUpperHddDrawerIntrusionCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Upper Hdd Drawer Intrusion Cleared" 
        --#SEVERITY INFORMATION
        ::= { IntelligentServerServerTRAPObject 356233 }
        
        
        
 -- Processor Middle Hdd Drawer Intrusion 
     IntelligentServerMiddleHddDrawerIntrusion TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        --#SEVERITY INFO
        DESCRIPTION
            "Middle Hdd Drawer Intrusion" 
        ::= 356106
    IntelligentServerMiddleHddDrawerIntrusion-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        --#SEVERITY INFO
        DESCRIPTION
            "Middle Hdd Drawer Intrusion" 
        ::= { IntelligentServerServerTRAPObject 356106 }
        
-- Processor Middle Hdd Drawer Intrusion Cleared 
    IntelligentServerMiddleHddDrawerIntrusionCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Middle Hdd Drawer Intrusion Cleared" 
        --#SEVERITY INFORMATION
        ::= 356234
    IntelligentServerMiddleHddDrawerIntrusionCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Middle Hdd Drawer Intrusion Cleared" 
        --#SEVERITY INFORMATION
        ::= { IntelligentServerServerTRAPObject 356234 }     
        
        
 -- Processor Lower Hdd Drawer Intrusion 
     IntelligentServerLowerHddDrawerIntrusion TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        --#SEVERITY INFO
        DESCRIPTION
            "Lower Hdd Drawer Intrusion" 
        ::= 356107
    IntelligentServerLowerHddDrawerIntrusion-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        --#SEVERITY INFO
        DESCRIPTION
            "Lower Hdd Drawer Intrusion" 
        ::= { IntelligentServerServerTRAPObject 356107 }
        
-- Processor Lower Hdd Drawer Intrusion Cleared 
    IntelligentServerLowerHddDrawerIntrusionCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Lower Hdd Drawer Intrusion Cleared" 
        --#SEVERITY INFORMATION
        ::= 356235
    IntelligentServerLowerHddDrawerIntrusionCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Lower Hdd Drawer Intrusion Cleared" 
        --#SEVERITY INFORMATION
        ::= { IntelligentServerServerTRAPObject 356235 }         
        

-- NTP SYNC Fail
    IntelligentServerChassisNTPSYNCFail TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "NTP SYNC Fail" 
        --#SEVERITY INFORMATION
        ::= 1601281
    IntelligentServerChassisNTPSYNCFail-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "NTP SYNC Fail" 
        --#SEVERITY INFORMATION
        ::= { IntelligentServerServerTRAPObject 1601281 }

-- **********************************************
--* Platform Security                          * 
-- **********************************************
-- Secure Mode Violation Attempt 
    IntelligentServerSecureModeViolation TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Secure Mode Violation Attempt" 
        --#SEVERITY CRITICAL
        ::= 421632
    IntelligentServerSecureModeViolation-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Secure Mode Violation Attempt" 
        --#SEVERITY CRITICAL
        ::= { IntelligentServerServerTRAPObject 421632 }
 
-- User Password Violation Attempt 
    IntelligentServerUserPasswordViolation TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
        "User Password Violation Attempt" 
        --#SEVERITY CRITICAL
        ::= 421633
    IntelligentServerUserPasswordViolation-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
        "User Password Violation Attempt" 
        --#SEVERITY CRITICAL
        ::= { IntelligentServerServerTRAPObject 421633 }

--  Setup Password Violation Attempt 
    IntelligentServerSetupPasswordViolation TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Setup Password Violation Attempt" 
        --#SEVERITY CRITICAL
        ::= 421634
    IntelligentServerSetupPasswordViolation-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Setup Password Violation Attempt" 
        --#SEVERITY CRITICAL
        ::= { IntelligentServerServerTRAPObject 421634 }
 
-- Network Boot Password Violation Attempt 
    IntelligentServerNetworkBootPasswordViolation TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Network Boot Password Violation Attempt"
        --#SEVERITY CRITICAL
        ::= 421635
    IntelligentServerNetworkBootPasswordViolation-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Network Boot Password Violation Attempt"
        --#SEVERITY CRITICAL
        ::= { IntelligentServerServerTRAPObject 421635 }
 
-- Other Pre-boot Password Violation Attempt 
    IntelligentServerOtherPasswordViolation TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Other Pre-boot Password Violation Attempt" 
        --#SEVERITY CRITICAL
        ::= 421636
    IntelligentServerOtherPasswordViolation-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Other Pre-boot Password Violation Attempt" 
        --#SEVERITY CRITICAL
        ::= { IntelligentServerServerTRAPObject 421636 }
 
--  Out-of-band access Password Violation Attempt 
    IntelligentServerOutOfBandAccessViolation TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Out-of-band access Violation Attempt" 
        --#SEVERITY CRITICAL
        ::= 421637
    IntelligentServerOutOfBandAccessViolation-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Out-of-band access Violation Attempt" 
        --#SEVERITY CRITICAL
        ::= { IntelligentServerServerTRAPObject 421637 }
 
--  Secure Mode Violation Attempt Cleared 
    IntelligentServerSecureModeViolationCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Secure Mode Violation Attempt Cleared" 
        --#SEVERITY INFORMATION
        ::= 421760
    IntelligentServerSecureModeViolationCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Secure Mode Violation Attempt Cleared" 
        --#SEVERITY INFORMATION
        ::= { IntelligentServerServerTRAPObject 421760 }
 
--  User Password Violation Attempt Cleared  
    IntelligentServerUserPasswordViolationCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "User Password Violation Attempt Cleared" 
        --#SEVERITY INFORMATION
        ::= 421761
    IntelligentServerUserPasswordViolationCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "User Password Violation Attempt Cleared" 
        --#SEVERITY INFORMATION
        ::= { IntelligentServerServerTRAPObject 421761 }

-- Setup Password Violation Attempt Cleared 
    IntelligentServerSetupPasswordViolationCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Setup Password Violation Attempt Cleared" 
        --#SEVERITY INFORMATION
        ::= 421762
    IntelligentServerSetupPasswordViolationCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Setup Password Violation Attempt Cleared" 
        --#SEVERITY INFORMATION
        ::= { IntelligentServerServerTRAPObject 421762 }
 
--  Network Boot Password Violation Attempt Cleared 
    IntelligentServerNetworkBootPasswordViolationCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Network Boot Password Violation Attempt Cleared" 
        --#SEVERITY INFORMATION
        ::= 421763
    IntelligentServerNetworkBootPasswordViolationCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Network Boot Password Violation Attempt Cleared" 
        --#SEVERITY INFORMATION
        ::= { IntelligentServerServerTRAPObject 421763 }
 
--  Other Pre-boot Password Violation Attempt Cleared 
    IntelligentServerOtherPasswordViolationCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Other Pre-boot Password Violation Attempt Cleared"
        --#SEVERITY INFORMATION
        ::= 421764
    IntelligentServerOtherPasswordViolationCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Other Pre-boot Password Violation Attempt Cleared"
        --#SEVERITY INFORMATION
        ::= { IntelligentServerServerTRAPObject 421764 }
 
--  Out-of-band access Password Violation Attempt Cleared 
        IntelligentServerOutOfBandAccessViolationCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Out-of-band access Violation Attempt Cleared" 
        --#SEVERITY INFORMATION
        ::= 421765
        IntelligentServerOutOfBandAccessViolationCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Out-of-band access Violation Attempt Cleared" 
        --#SEVERITY INFORMATION
        ::= { IntelligentServerServerTRAPObject 421765 }
        
-- **********************************************
--* Processor                                   * 
-- **********************************************

-- Processor Thermal Trip Occured 
    IntelligentServerProcessorThermalTripOccured TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Thermal Trip Occured"
        --#SEVERITY CRITICAL
        ::= 460545
    IntelligentServerProcessorThermalTripOccured-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Thermal Trip Occured"
        --#SEVERITY CRITICAL
        ::= { IntelligentServerServerTRAPObject 460545 }
        
-- Processor CPU Pin Out Prochot Asserted
    IntelligentServerProcessorCPUPinOutProchotAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor CPU Pin Out Prochot Asserted"
        --#SEVERITY CRITICAL
        ::= 460593
    IntelligentServerProcessorCPUPinOutProchotAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor CPU Pin Out Prochot Asserted"
        --#SEVERITY CRITICAL
        ::= { IntelligentServerServerTRAPObject 460593 }
        
-- Processor CPU Pin Out Prochot Deasserted
    IntelligentServerProcessorCPUPinOutProchotDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor CPU Pin Out Prochot Deasserted"
        --#SEVERITY CRITICAL
        ::= 460721
    IntelligentServerProcessorCPUPinOutProchotDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor CPU Pin Out Prochot Deasserted"
        --#SEVERITY CRITICAL
        ::= { IntelligentServerServerTRAPObject 460721 }
-- Processor CPU Pin Out thermal trip Asserted
    IntelligentServerProcessorCPUPinOutThermalTripAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor CPU Pin Out Thermal Trip Asserted"
        --#SEVERITY CRITICAL
        ::= 460594
    IntelligentServerProcessorCPUPinOutThermalTripAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor CPU Pin Out Thermal Trip Asserted"
        --#SEVERITY CRITICAL
        ::= { IntelligentServerServerTRAPObject 460594 }
        
-- Processor CPU Pin Out thermal trip Deasserted
    IntelligentServerProcessorCPUPinOutThermalTripDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor CPU Pin Out Thermal Trip Deasserted"
        --#SEVERITY CRITICAL
        ::= 460722
    IntelligentServerProcessorCPUPinOutThermalTripDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor CPU Pin Out Thermal Trip Deasserted"
        --#SEVERITY CRITICAL
        ::= { IntelligentServerServerTRAPObject 460722 }

-- Processor internal error 
    IntelligentServerProcessorInternalError TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Internal Error"
        --#SEVERITY CRITICAL
        ::= 487168
    IntelligentServerProcessorInternalError-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Internal Error"
        --#SEVERITY CRITICAL
        ::= { IntelligentServerServerTRAPObject 487168 }
 
-- Processor Thermal Trip 
    IntelligentServerProcessorThermalTrip TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Thermal Trip (Over Temperature Shutdown)"
        --#SEVERITY CRITICAL
        ::= 487169
    IntelligentServerProcessorThermalTrip-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Thermal Trip (Over Temperature Shutdown)"
        --#SEVERITY CRITICAL
        ::= { IntelligentServerServerTRAPObject 487169 }

--Processor Fault Resilient Booting (FRB) 1 / Built-in self test (BIST) Error 
    IntelligentServerProcessorBistError TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Processor Fault Resilient Booting (FRB) 1 / BIST (Built In Self Test) Failure" 
        --#SEVERITY WARNING
        ::= 487170
    IntelligentServerProcessorBistError-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Processor Fault Resilient Booting (FRB) 1 / BIST (Built In Self Test) Failure" 
        --#SEVERITY WARNING
        ::= { IntelligentServerServerTRAPObject 487170 }

--Processor Fault Resilient Booting (FRB) 2 / Hang in Power On Self Test (POST) 
    IntelligentServerProcessorFRB2Failure TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Fault Resilient Booting (FRB) 2 / Hang in Power On Self Test (POST) Failure" 
        --#SEVERITY CRITICAL 
        ::= 487171
    IntelligentServerProcessorFRB2Failure-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Fault Resilient Booting (FRB) 2 / Hang in Power On Self Test (POST) Failure" 
        --#SEVERITY CRITICAL 
        ::= { IntelligentServerServerTRAPObject 487171 }

--Processor Fault Resilient Booting (FRB) 3 / Processor Setup / Initialization Failure 
    IntelligentServerProcessorFRB3Failure TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Fault Resilient Booting (FRB) 3 / Processor Setup / Initialization Failure" 
        --#SEVERITY CRITICAL
        ::= 487172
    IntelligentServerProcessorFRB3Failure-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Fault Resilient Booting (FRB) 3 / Processor Setup / Initialization Failure" 
        --#SEVERITY CRITICAL
        ::= { IntelligentServerServerTRAPObject 487172 }

--Processor config error 
    IntelligentServerProcessorConfigError TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Configuration Error" 
        --#SEVERITY WARNING
        ::= 487173
    IntelligentServerProcessorConfigError-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Configuration Error" 
        --#SEVERITY WARNING
        ::= { IntelligentServerServerTRAPObject 487173 }
 
-- SM BIOS Uncorrectable CPU-complex Error 
    IntelligentServerSMPIOSUncorrectableCPUComplexError TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "SM BIOS Uncorrectable CPU-complex Error" 
        --#SEVERITY CRITICAL
        ::= 487174
    IntelligentServerSMPIOSUncorrectableCPUComplexError-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "SM BIOS Uncorrectable CPU-complex Error" 
        --#SEVERITY CRITICAL
        ::= { IntelligentServerServerTRAPObject 487174 }
 
 -- Processor Presence Detected 
     IntelligentServerProcessorPresenceDetected TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Presence Detected" 
        --#SEVERITY INFORMATION
        ::= 487175
    IntelligentServerProcessorPresenceDetected-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Presence Detected" 
        --#SEVERITY INFORMATION
        ::= { IntelligentServerServerTRAPObject 487175 }
 
-- Processor Disabled 
    IntelligentServerProcessorDisabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Disabled"
        --#SEVERITY INFORMATION
        ::= 487176
    IntelligentServerProcessorDisabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Disabled"
        --#SEVERITY INFORMATION
        ::= { IntelligentServerServerTRAPObject 487176 }
 
-- Terminator Presence Detected 
    IntelligentServerTerminatorresenceDetected TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Terminator Presence Detected" 
        --#SEVERITY INFORMATION
        ::= 487177
    IntelligentServerTerminatorresenceDetected-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Terminator Presence Detected" 
        --#SEVERITY INFORMATION
        ::= { IntelligentServerServerTRAPObject 487177 }
 
-- Processor throttle. 
    IntelligentServerProcessorThrottle TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Throttled (Processor Speed Reduced)" 
        --#SEVERITY   WARNING
        ::= 487178
    IntelligentServerProcessorThrottle-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Throttled (Processor Speed Reduced)" 
        --#SEVERITY   WARNING
        ::= { IntelligentServerServerTRAPObject 487178 }
		
-- Processor machine check excep. 
    IntelligentServerProcessorMachineCheckExcep TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Machine Check Excep" 
        --#SEVERITY   CRITICAL
        ::= 487179
    IntelligentServerProcessorMachineCheckExcep-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Machine Check Excep" 
        --#SEVERITY   CRITICAL
        ::= { IntelligentServerServerTRAPObject 487179 }
		
-- Processor machine check error. 
    IntelligentServerProcessorMachineCheckError TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Machine Check Error" 
        --#SEVERITY   WARNING
        ::= 487180
    IntelligentServerProcessorMachineCheckError-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Machine Check Error" 
        --#SEVERITY   WARNING
        ::= { IntelligentServerServerTRAPObject 487180 }

-- Processor Core Disable. 
    IntelligentServerProcessorCoreDisable TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Core Disable" 
        --#SEVERITY   CRITICAL
        ::= 487181
    IntelligentServerProcessorCoreDisable-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Machine Core Disable" 
        --#SEVERITY   CRITICAL
        ::= { IntelligentServerServerTRAPObject 487181 }

-- Processor Socket Disable. 
    IntelligentServerProcessorSocketDisable TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Socket Disable" 
        --#SEVERITY   CRITICAL
        ::= 487182
    IntelligentServerProcessorSocketDisable-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Socket Disable" 
        --#SEVERITY   CRITICAL
        ::= { IntelligentServerServerTRAPObject 487182 }
        
-- Processor Machine Check Excep
    IntelligentServerCPUMachineCheckExcep TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Machine Check Excep" 
        --#SEVERITY   CRITICAL
        ::= 487211
    IntelligentServerCPUMachineCheckExcep-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Machine Check Excep" 
        --#SEVERITY   CRITICAL
        ::= { IntelligentServerServerTRAPObject 487211 }
        
-- Processor Machine Check Error 
    IntelligentServerCPUCorrectableMachineCheckError TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Correctable Machine Check Error" 
        --#SEVERITY   CRITICAL
        ::= 487212
    IntelligentServerCPUCorrectableMachineCheckError-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Correctable Machine Check Error" 
        --#SEVERITY   CRITICAL
        ::= { IntelligentServerServerTRAPObject 487212 }
 
-- Processor internal error cleared 
    IntelligentServerProcessorInternalErrorCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Internal Error Cleared" 
        --#SEVERITY INFORMATION
        ::= 487296
    IntelligentServerProcessorInternalErrorCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Internal Error Cleared" 
        --#SEVERITY INFORMATION
        ::= { IntelligentServerServerTRAPObject 487296 }

--Processor Back to normal from Thermal Trip 
    IntelligentServerProcessorThermalTripCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Thermal Trip (Over Temperature Shutdown) Cleared" 
        --#SEVERITY INFORMATION
        ::= 487297
    IntelligentServerProcessorThermalTripCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Thermal Trip (Over Temperature Shutdown) Cleared" 
        --#SEVERITY INFORMATION
        ::= { IntelligentServerServerTRAPObject 487297 }
 
-- Processor BIST Error cleared 
    IntelligentServerProcessorBistErrorCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor BIST (Built In Self Test) Failure Cleared" 
        --#SEVERITY INFORMATION
        ::= 487298
    IntelligentServerProcessorBistErrorCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor BIST (Built In Self Test) Failure Cleared" 
        --#SEVERITY INFORMATION
        ::= { IntelligentServerServerTRAPObject 487298 }

--Processor Fault Resilient Booting (FRB) 2 / Hang in Power On Self Test (POST) Cleared 
    IntelligentServerProcessorFRB2FailureCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Fault Resilient Booting (FRB) 2 / Hang in Power On Self Test (POST) Failure Cleared" 
        --#SEVERITY INFORMATION 
        ::= 487299
    IntelligentServerProcessorFRB2FailureCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Fault Resilient Booting (FRB) 2 / Hang in Power On Self Test (POST) Failure Cleared" 
        --#SEVERITY INFORMATION 
        ::= { IntelligentServerServerTRAPObject 487299 }
 
-- Processor Fault Resilient Booting (FRB) 3 / Processor Setup / Initialization Failure Cleared 
    IntelligentServerProcessorFRB3FailureCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Processor Fault Resilient Booting (FRB) 3 / Processor Setup / Initialization Failure Cleared" 
        --#SEVERITY INFORMATION
        ::= 487300
    IntelligentServerProcessorFRB3FailureCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Processor Fault Resilient Booting (FRB) 3 / Processor Setup / Initialization Failure Cleared" 
        --#SEVERITY INFORMATION
        ::= { IntelligentServerServerTRAPObject 487300 }
 
-- Processor config error cleared 
    IntelligentServerProcessorConfigErrorCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Processor Configuration Error Cleared" 
        --#SEVERITY INFORMATION
        ::= 487301
    IntelligentServerProcessorConfigErrorCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Processor Configuration Error Cleared" 
        --#SEVERITY INFORMATION
        ::= { IntelligentServerServerTRAPObject 487301 }
 
-- SM BIOS Uncorrectable CPU-complex Error Cleared 
    IntelligentServerSMPIOSUncorrectableCPUComplexErrorCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SM BIOS Uncorrectable CPU-complex Error Cleared" 
        --#SEVERITY CRITICAL
        ::= 487302
    IntelligentServerSMPIOSUncorrectableCPUComplexErrorCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SM BIOS Uncorrectable CPU-complex Error Cleared" 
        --#SEVERITY CRITICAL
        ::= { IntelligentServerServerTRAPObject 487302 }

-- Processor Presence detected Assert 
    IntelligentServerProcessorPresenceDetectedAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Presence detected" 
        --#SEVERITY INFORMATION
        ::= 487303
    IntelligentServerProcessorPresenceDetectedAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Presence detected" 
        --#SEVERITY INFORMATION
        ::= { IntelligentServerServerTRAPObject 487303 }
 
-- Processor return to normal from throttled 
    IntelligentServerProcessorThrottleCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Throttle Cleared (Normal Processor Speed)"
        --#SEVERITY INFORMATION
        ::= 487306
    IntelligentServerProcessorThrottleCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Throttle Cleared (Normal Processor Speed)"
        --#SEVERITY INFORMATION
        ::= { IntelligentServerServerTRAPObject 487306 }

-- Processor machine check exception Dessarted. 
    IntelligentServerProcessorMachineCheckExceptionDessarted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Machine Check Exception (Uncorrectable) Dessarted" 
        --#SEVERITY   CRITICAL
        ::= 487307
    IntelligentServerProcessorMachineCheckExceptionDessarted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Machine Check Exception (Uncorrectable) Dessarted" 
        --#SEVERITY   CRITICAL
        ::= { IntelligentServerServerTRAPObject 487307 }

-- Correctable Machine Check Error Cleared 
    IntelligentServerCorrectableMachineCheckErrorCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Correctable Machine Check Error Cleared" 
        --#SEVERITY INFORMATION
        ::= 487308
    IntelligentServerCorrectableMachineCheckErrorCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Correctable Machine Check Error Cleared" 
        --#SEVERITY INFORMATION
        ::= { IntelligentServerServerTRAPObject 487308 }

-- Processor Generic State Deasserted 
    ProcessorGenericStateDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Generic State Deasserted"
        --#SEVERITY INFORMATION
        ::= 459520
    ProcessorGenericStateDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Generic State Deasserted"
        --#SEVERITY INFORMATION
        ::= { IntelligentServerServerTRAPObject 459520 }

-- Processor Generic State Asserted 
    ProcessorGenericStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor Generic State Asserted"
        --#SEVERITY INFORMATION
        ::= 459521
    ProcessorGenericStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor Generic State Asserted"
        --#SEVERITY INFORMATION
        ::= { IntelligentServerServerTRAPObject 459521 }
 
-- ********************************************** 
-- *    Power Supply                           * 
-- ********************************************** 

-- Power Supply State Deasserted 
    IntelligentServerPowerSupplyStateDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply is disconnected from AC Power." 
        --#SEVERITY CRITICAL
        ::= 525056
    IntelligentServerPowerSupplyStateDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply is disconnected from AC Power." 
        --#SEVERITY CRITICAL
        ::= { IntelligentServerServerTRAPObject 525056 }

--Power Supply State Asserted 
    IntelligentServerPowerSupplyStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply is connected to AC Power."
        --#SEVERITY INFORMATION
        ::= 525057
    IntelligentServerPowerSupplyStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply is connected to AC Power."
        --#SEVERITY INFORMATION
        ::= { IntelligentServerServerTRAPObject 525057 }

--Predictive Failure Deasserted 
    IntelligentServerPowerSupplyPredictiveFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Predictive Failure Deasserted"
        --#SEVERITY CRITICAL
        ::= 525313
    IntelligentServerPowerSupplyPredictiveFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Predictive Failure Deasserted"
        --#SEVERITY CRITICAL
        ::= { IntelligentServerServerTRAPObject 525313 }

--Predictive Failure Asserted 
    IntelligentServerPowerSupplyPredictiveFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Predictive Failure Asserted"
        --#SEVERITY INFORMATION
        ::= 525312
    IntelligentServerPowerSupplyPredictiveFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Predictive Failure Asserted"
        --#SEVERITY INFORMATION
        ::= { IntelligentServerServerTRAPObject 525312 }
 
-- Power Supply Full Redundancy  
    IntelligentServerPowerSupplyFullRedundancy TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Redundancy Has Returned to Normal"
        --#SEVERITY INFORMATION
        ::= 527104
    IntelligentServerPowerSupplyFullRedundancy-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Redundancy Has Returned to Normal"
        --#SEVERITY INFORMATION
        ::= { IntelligentServerServerTRAPObject 527104 }

--Power Supply Redundancy lost  
    IntelligentServerPowerSupplyRedundancyLost TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Redundancy has been Lost"
        --#SEVERITY CRITICAL
        ::= 527105
    IntelligentServerPowerSupplyRedundancyLost-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Redundancy has been Lost"
        --#SEVERITY CRITICAL
        ::= { IntelligentServerServerTRAPObject 527105 }

--Power Supply Redundancy degraded 
    IntelligentServerPowerSupplyRedundancyDegraded TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Redundancy is in a degraded state"
        --#SEVERITY WARNING
        ::= 527106
    IntelligentServerPowerSupplyRedundancyDegraded-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Redundancy is in a degraded state"
        --#SEVERITY WARNING
        ::= { IntelligentServerServerTRAPObject 527106 }
        
-- Power Supply Full Redundancy Deasserted
    IntelligentServerPowerSupplyFullRedundancyDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Full Redundancy Deasserted"
        --#SEVERITY INFORMATION
        ::= 527232
    IntelligentServerPowerSupplyFullRedundancyDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Full Redundancy Deasserted"
        --#SEVERITY INFORMATION
        ::= { IntelligentServerServerTRAPObject 527232 }
		
--Power Supply Redundancy Has Returned to Normal 
    IntelligentServerPowerSupplyRedundancyHasReturnedtoNormal TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Redundancy Has Returned to Normal"
        --#SEVERITY WARNING
        ::= 527233
    IntelligentServerPowerSupplyRedundancyHasReturnedtoNormal-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Redundancy Has Returned to Normal"
        --#SEVERITY WARNING
        ::= { IntelligentServerServerTRAPObject 527233 }

--Power Supply presence detected 
    IntelligentServerPowerSupplyPresenceDeteced TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Inserted"
        --#SEVERITY INFORMATION
        ::= 552704
    IntelligentServerPowerSupplyPresenceDeteced-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Inserted"
        --#SEVERITY INFORMATION
        ::= { IntelligentServerServerTRAPObject 552704 }

    IntelligentServerPowerSupplyFailureDetected TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power supply Failure detected"
        --#SEVERITY CRITICAL
        ::= 552705
    IntelligentServerPowerSupplyFailureDetected-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power supply Failure detected"
        --#SEVERITY CRITICAL
        ::= { IntelligentServerServerTRAPObject 552705 }

    IntelligentServerPowerSupplyWarning TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power supply Warning"
        --#SEVERITY WARNING
        ::= 552706
    IntelligentServerPowerSupplyWarning-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power supply Warning"
        --#SEVERITY WARNING
        ::= { IntelligentServerServerTRAPObject 552706 }

--AC Lost 
    IntelligentServerPowerSupplyACLost TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply AC Lost"
        --#SEVERITY CRITICAL
        ::= 552707
    IntelligentServerPowerSupplyACLost-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply AC Lost"
        --#SEVERITY CRITICAL
        ::= { IntelligentServerServerTRAPObject 552707 }

-- Power Supply input lost or out-of-range 
    IntelligentServerPowerSupplyInputLost TRAP-TYPE
    OBJECTS { altHostLocation, altTrapTime, altSysManufacture, altSysModel, altSensorName, altSensorType, altSensorReading, altSensorThreshold, altHostContact, altBMCHostName, altSysName, altSpTxtId, altPriority, altEventAssertOrDeassert }
    STATUS current
    ENTERPRISE IntelligentServerServerTRAPObject
    DESCRIPTION
        "Power Supply input lost or out-of-range" 
        --#SEVERITY CRITICAL
    ::= 552708
    IntelligentServerPowerSupplyInputLost-V2cV3 NOTIFICATION-TYPE
    OBJECTS { altHostLocation, altTrapTime, altSysManufacture, altSysModel, altSensorName, altSensorType, altSensorReading, altSensorThreshold, altHostContact, altBMCHostName, altSysName, altSpTxtId, altPriority, altEventAssertOrDeassert }
    STATUS current
    DESCRIPTION
        "Power Supply input lost or out-of-range" 
        --#SEVERITY CRITICAL
    ::= { IntelligentServerServerTRAPObject 552708 }
 
--  Power Supply input out-of-range, but present 
    IntelligentServerPowerSupplyInputOutOfRange TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply input out-of-range, but present"
        --#SEVERITY CRITICAL
        ::= 552709
    IntelligentServerPowerSupplyInputOutOfRange-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply input out-of-range, but present"
        --#SEVERITY CRITICAL
        ::= { IntelligentServerServerTRAPObject 552709 }
 
-- Configuration error 
    IntelligentServerPowerSupplyConfigError TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Configuration error"
        --#SEVERITY CRITICAL
        ::= 552710
    IntelligentServerPowerSupplyConfigError-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Configuration error"
        --#SEVERITY CRITICAL
        ::= { IntelligentServerServerTRAPObject 552710 }

-- Abnormal Power Failure of Mainboard
    IntelligentServerMainboardAbnormalPowerFailure TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Abnormal Power Failure of Mainboard"
        --#SEVERITY CRITICAL
        ::= 552752
    IntelligentServerMainboardAbnormalPowerFailure-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Abnormal Power Failure of Mainboard"
        --#SEVERITY CRITICAL
        ::= { IntelligentServerServerTRAPObject 552752 }

-- Mainboard Power Timeout
    IntelligentServerMainboardPowerTimeout TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Mainboard Power Timeout"
        --#SEVERITY CRITICAL
        ::= 552753
    IntelligentServerMainboardPowerTimeout-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Mainboard Power Timeout"
        --#SEVERITY CRITICAL
        ::= { IntelligentServerServerTRAPObject 552753 }
 
-- Power Supply removed 
    IntelligentServerPowerSupplyPresenceRemoved TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Removed" 
        --#SEVERITY WARNING
        ::= 552832
    IntelligentServerPowerSupplyPresenceRemoved-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Removed" 
        --#SEVERITY WARNING
        ::= { IntelligentServerServerTRAPObject 552832 }

--Back to normal from failure 
    IntelligentServerPowerSupplyFailureCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Failure Cleared" 
        --#SEVERITY INFORMATION
        ::= 552833
    IntelligentServerPowerSupplyFailureCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Failure Cleared" 
        --#SEVERITY INFORMATION
        ::= { IntelligentServerServerTRAPObject 552833 }

--Predictive Failure cleared  
    IntelligentServerPowerSupplyWarningCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Power Supply Warning Cleared"
        --#SEVERITY INFORMATION
        ::= 552834
    IntelligentServerPowerSupplyWarningCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Power Supply Warning Cleared"
        --#SEVERITY INFORMATION
        ::= { IntelligentServerServerTRAPObject 552834 }

--AC Back 
    IntelligentServerPowerSupplyACBack TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply AC Restored"
        --#SEVERITY INFORMATION
        ::= 552835
    IntelligentServerPowerSupplyACBack-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply AC Restored"
        --#SEVERITY INFORMATION
        ::= { IntelligentServerServerTRAPObject 552835 }

--  Power Supply input lost or out-of-range Restored 
    IntelligentServerPowerSupplyInputBack TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply input lost or out-of-range Restored" 
        --#SEVERITY INFORMATION
        ::= 552836
    IntelligentServerPowerSupplyInputBack-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply input lost or out-of-range Restored" 
        --#SEVERITY INFORMATION
        ::= { IntelligentServerServerTRAPObject 552836 }
 
--  Power Supply input out-of-range is restored 
    IntelligentServerPowerSupplyInputOutOfRangeRestored TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply input out-of-range restored"  
        --#SEVERITY INFORMATION
        ::= 552837
    IntelligentServerPowerSupplyInputOutOfRangeRestored-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply input out-of-range restored"  
        --#SEVERITY INFORMATION
        ::= { IntelligentServerServerTRAPObject 552837 }
     
-- Configuration error Cleared 
        IntelligentServerPowerSupplyConfigErrorCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply Configuration error Cleared" 
        --#SEVERITY INFORMATION
        ::= 552838
    IntelligentServerPowerSupplyConfigErrorCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply Configuration error Cleared" 
        --#SEVERITY INFORMATION
        ::= { IntelligentServerServerTRAPObject 552838 }

-- ********************************************** 
-- *    Power Unit                             * 
-- ********************************************** 

-- Power Good Sensor events Deasserted 
    IntelligentServerPowerUnitStateDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Run-time power fault has occurred. This state indicates 
            that one or more DC-DC converter have failed or are not operating 
            within nominal specifications." 
        --#SEVERITY   CRITICAL
        ::= 590592
    IntelligentServerPowerUnitStateDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Run-time power fault has occurred. This state indicates 
            that one or more DC-DC converter have failed or are not operating 
            within nominal specifications." 
        --#SEVERITY   CRITICAL
        ::= { IntelligentServerServerTRAPObject 590592 }

--Power Good Sensor events Asserted 
    IntelligentServerPowerUnitStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Host power-on sequence has been completed successfully"
        --#SEVERITY   INFORMATION
        ::= 590593
    IntelligentServerPowerUnitStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Host power-on sequence has been completed successfully"
        --#SEVERITY   INFORMATION
        ::= { IntelligentServerServerTRAPObject 590593 }

-- Power Unit Redundancy OK  
    IntelligentServerPowerUnitRedundancyOk TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Unit Redundancy has been restored"
        --#SEVERITY INFORMATION
        ::= 592640
    IntelligentServerPowerUnitRedundancyOk-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Unit Redundancy has been restored"
        --#SEVERITY INFORMATION
        ::= { IntelligentServerServerTRAPObject 592640 }

-- Power Unit Redundancy lost
    IntelligentServerPowerUnitRedundancyLost TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Unit Redundancy has been Lost" 
        --#SEVERITY CRITICAL
        ::= 592641
    IntelligentServerPowerUnitRedundancyLost-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Unit Redundancy has been Lost" 
        --#SEVERITY CRITICAL
        ::= { IntelligentServerServerTRAPObject 592641 }

-- Power Unit Redundancy resource lack
    IntelligentServerPowerUnitRedundancyResourceLack TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Unit Redundancy resource lack" 
        --#SEVERITY INFORMATION
        ::= 592645
    IntelligentServerPowerUnitRedundancyResourceLack-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Unit Redundancy resource lack" 
        --#SEVERITY INFORMATION
        ::= { IntelligentServerServerTRAPObject 592645 }

 -- Power Supply input lost or out-of-range Restored 
     IntelligentServerPowerSupplyInputRestored TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Supply input lost or out-of-range Restored" 
        --#SEVERITY INFORMATION
        ::= 592768
    IntelligentServerPowerSupplyInputRestored-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Supply input lost or out-of-range Restored" 
        --#SEVERITY INFORMATION
        ::= { IntelligentServerServerTRAPObject 592768 } 

 -- Power Unit Redundancy regain  
     IntelligentServerPowerUnitRedundancyRegain TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Unit Redundancy has been Lost" 
        --#SEVERITY INFORMATION
        ::= 592769
    IntelligentServerPowerUnitRedundancyRegain-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Unit Redundancy has been Lost" 
        --#SEVERITY INFORMATION
        ::= { IntelligentServerServerTRAPObject 592769 } 

 -- Power Unit Redundancy resource regain  
     IntelligentServerPowerUnitRedundancyResourceRegain TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Unit Redundancy resource regain" 
        --#SEVERITY INFORMATION 
        ::= 592773 
    IntelligentServerPowerUnitRedundancyResourceRegain-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Unit Redundancy resource regain" 
        --#SEVERITY INFORMATION 
        ::= { IntelligentServerServerTRAPObject 592773 } 

-- Power Off 
    IntelligentServerPowerUnitPowerOff TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power unit is off." 
        --#SEVERITY INFORMATION
        ::= 618240
    IntelligentServerPowerUnitPowerOff-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power unit is off." 
        --#SEVERITY INFORMATION
        ::= { IntelligentServerServerTRAPObject 618240 }
 
-- Power Cycle 
    IntelligentServerPowerUnitPowerCycle TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power unit is power cycled"
        --#SEVERITY INFORMATION
        ::= 618241
    IntelligentServerPowerUnitPowerCycle-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power unit is power cycled"
        --#SEVERITY INFORMATION
        ::= { IntelligentServerServerTRAPObject 618241 }
 
-- 240VA Power Down 
    IntelligentServerPowerUnit240VAPowerDown TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power unit 240VA Power Down" 
        --#SEVERITY INFORMATION
        ::= 618242
    IntelligentServerPowerUnit240VAPowerDown-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power unit 240VA Power Down" 
        --#SEVERITY INFORMATION
        ::= { IntelligentServerServerTRAPObject 618242 }
 
-- Interlock Power Down 
    IntelligentServerPowerUnitInterlockPowerDown TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power unit Interlock Power Down" 
        --#SEVERITY INFORMATION
        ::= 618243
    IntelligentServerPowerUnitInterlockPowerDown-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power unit Interlock Power Down" 
        --#SEVERITY INFORMATION
        ::= { IntelligentServerServerTRAPObject 618243 }
 
-- AC lost / Power input lost 
    IntelligentServerPowerUnitACLost TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power unit AC lost / Power input lost" 
        --#SEVERITY INFORMATION
        ::= 618244
    IntelligentServerPowerUnitACLost-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power unit AC lost / Power input lost" 
        --#SEVERITY INFORMATION
        ::= { IntelligentServerServerTRAPObject 618244 }
 
--  Soft Power Control Failure 
    IntelligentServerPowerUnitSoftPowerControlFail TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Soft Power Control Failure" 
        --#SEVERITY INFORMATION
        ::= 618245
    IntelligentServerPowerUnitSoftPowerControlFail-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Soft Power Control Failure" 
        --#SEVERITY INFORMATION
        ::= { IntelligentServerServerTRAPObject 618245 }
 
-- Power Unit Failure detected 
    IntelligentServerPowerUnitFailure TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Unit Failure detected"
        --#SEVERITY WARNING
        ::= 618246
    IntelligentServerPowerUnitFailure-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Unit Failure detected"
        --#SEVERITY WARNING
        ::= { IntelligentServerServerTRAPObject 618246 }
 
-- Predictive Failure 
    IntelligentServerPowerUnitPredictiveFailure TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Unit Predictive Failure" 
        --#SEVERITY WARNING
        ::= 618247
    IntelligentServerPowerUnitPredictiveFailure-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Unit Predictive Failure" 
        --#SEVERITY WARNING
        ::= { IntelligentServerServerTRAPObject 618247 }
 
-- Power Unit On 
    IntelligentServerPowerUnitPowerOn TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Power Unit is on."
        --#SEVERITY INFORMATION
        ::= 618248
    IntelligentServerPowerUnitPowerOn-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Power Unit is on."
        --#SEVERITY INFORMATION
		::= { IntelligentServerServerTRAPObject 618248 }

-- Power Cycle Completed
    IntelligentServerPowerUnitPowerCycleCompleted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Power unit - Power Cycle Completed" 
        --#SEVERITY INFORMATION
        ::= 618369
    IntelligentServerPowerUnitPowerCycleCompleted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Power unit - Power Cycle Completed" 
        --#SEVERITY INFORMATION
        ::= { IntelligentServerServerTRAPObject 618369 }
 
-- 240VA Power Down 
    IntelligentServerPowerUnit240VAPowerUp TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power unit 240VA Power Up" 
        --#SEVERITY INFORMATION
        ::= 618370
    IntelligentServerPowerUnit240VAPowerUp-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power unit 240VA Power Up" 
        --#SEVERITY INFORMATION
        ::= { IntelligentServerServerTRAPObject 618370 }
 
-- Interlock Power Up 
    IntelligentServerPowerUnitInterlockPowerUp TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power unit Interlock Power Up" 
        --#SEVERITY INFORMATION
        ::= 618371
    IntelligentServerPowerUnitInterlockPowerUp-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power unit Interlock Power Up" 
        --#SEVERITY INFORMATION
        ::= { IntelligentServerServerTRAPObject 618371 }
 
-- AC/Power input restored 
    IntelligentServerPowerUnitACRestored TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power unit AC/Power input restored" 
        --#SEVERITY INFORMATION
        ::= 618372
    IntelligentServerPowerUnitACRestored-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power unit AC/Power input restored" 
        --#SEVERITY INFORMATION
        ::= { IntelligentServerServerTRAPObject 618372 }
     
-- Soft Power Control Failure Cleared 
    IntelligentServerPowerUnitSoftPowerControlFailCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Soft Power Control Failure Cleared" 
        --#SEVERITY INFORMATION
        ::= 618373
    IntelligentServerPowerUnitSoftPowerControlFailCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Soft Power Control Failure Cleared" 
        --#SEVERITY INFORMATION
        ::= { IntelligentServerServerTRAPObject 618373 }
 
-- Power Unit Failure Cleared 
    IntelligentServerPowerUnitFailureCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Unit Failure Cleared" 
        --#SEVERITY INFORMATION
        ::= 618374
    IntelligentServerPowerUnitFailureCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Unit Failure Cleared" 
        --#SEVERITY INFORMATION
        ::= { IntelligentServerServerTRAPObject 618374 }
 
-- Predictive Failure Cleared 
    IntelligentServerPowerUnitPredictiveFailureCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Power Unit Predictive Failure Cleared"
        --#SEVERITY INFORMATION
        ::= 618375
    IntelligentServerPowerUnitPredictiveFailureCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Power Unit Predictive Failure Cleared"
        --#SEVERITY INFORMATION
        ::= { IntelligentServerServerTRAPObject 618375 }

-- ********************************************** 
-- *        Cooling Device                     * 
-- ********************************************** 

-- Cooling Device speed has decreased below lower non-critical threshold 
    IntelligentServerCoolingDeviceUnderSpeedWarningLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cooling Device Under Speed Warning (Lower non-critical, going low)" 
        --#SEVERITY WARNING
        ::= 655616
    IntelligentServerCoolingDeviceUnderSpeedWarningLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cooling Device Under Speed Warning (Lower non-critical, going low)" 
        --#SEVERITY WARNING
        ::= { IntelligentServerServerTRAPObject 655616 }
 
-- Cooling Device speed has increased above lower non-critical threshold 
    IntelligentServerCoolingDeviceUnderSpeedWarningHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cooling Device Under Speed Warning (Lower non-critical, going high)" 
        --#SEVERITY WARNING
        ::= 655617
    IntelligentServerCoolingDeviceUnderSpeedWarningHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cooling Device Under Speed Warning (Lower non-critical, going high)" 
        --#SEVERITY WARNING
        ::= { IntelligentServerServerTRAPObject 655617 }
 
-- Cooling Device speed has decreased below lower critical threshold 
    IntelligentServerCoolingDeviceUnderSpeedCriticalLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Under Speed problem (Lower critical, going low)" 
        --#SEVERITY CRITICAL
        ::= 655618
    IntelligentServerCoolingDeviceUnderSpeedCriticalLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Under Speed problem (Lower critical, going low)" 
        --#SEVERITY CRITICAL
        ::= { IntelligentServerServerTRAPObject 655618 }
 
-- Cooling Device speed has increased above lower critical threshold 
    IntelligentServerCoolingDeviceUnderSpeedCriticalHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Under Speed problem (Lower critical, going high)" 
        --#SEVERITY CRITICAL
        ::= 655619
    IntelligentServerCoolingDeviceUnderSpeedCriticalHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Under Speed problem (Lower critical, going high)" 
        --#SEVERITY CRITICAL
        ::= { IntelligentServerServerTRAPObject 655619 }
 
-- Cooling Device speed has decreased below lower non-recoverable threshold 
    IntelligentServerCoolingDeviceUnderSpeedNonRecoverableLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Under Speed problem (Lower non-recoverable, going low)" 
        --#SEVERITY CRITICAL
        ::= 655620
    IntelligentServerCoolingDeviceUnderSpeedNonRecoverableLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Under Speed problem (Lower non-recoverable, going low)" 
        --#SEVERITY CRITICAL
        ::= { IntelligentServerServerTRAPObject 655620 }
 
-- Cooling Device speed has increased above lower non-recoverable threshold 
    IntelligentServerCoolingDeviceUnderSpeedNonRecoverableHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Under Speed problem (Lower non-recoverable, going high)" 
        --#SEVERITY CRITICAL
        ::= 655621
    IntelligentServerCoolingDeviceUnderSpeedNonRecoverableHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Under Speed problem (Lower non-recoverable, going high)" 
        --#SEVERITY CRITICAL
        ::= { IntelligentServerServerTRAPObject 655621 }
 
-- Cooling Device speed has decreased below Upper non-critical threshold 
    IntelligentServerCoolingDeviceOverSpeedWarningLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cooling Device Over Speed Warning (Upper non-critical, going low)" 
        --#SEVERITY WARNING
        ::= 655622
    IntelligentServerCoolingDeviceOverSpeedWarningLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cooling Device Over Speed Warning (Upper non-critical, going low)" 
        --#SEVERITY WARNING
        ::= { IntelligentServerServerTRAPObject 655622 }
 
-- Cooling Device speed has increased above upper non-critical threshold. 
    IntelligentServerCoolingDeviceOverSpeedWarningHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cooling Device Over Speed Warning (Upper non-critical, going high)" 
        --#SEVERITY WARNING
        ::= 655623
    IntelligentServerCoolingDeviceOverSpeedWarningHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cooling Device Over Speed Warning (Upper non-critical, going high)" 
        --#SEVERITY WARNING
        ::= { IntelligentServerServerTRAPObject 655623 }
 
-- Cooling Device speed has decreased below Upper critical threshold 
    IntelligentServerCoolingDeviceOverSpeedCriticalLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Cooling Device Over Speed problem (Upper critical, going low)"
        --#SEVERITY CRITICAL
        ::= 655624
    IntelligentServerCoolingDeviceOverSpeedCriticalLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Cooling Device Over Speed problem (Upper critical, going low)"
        --#SEVERITY CRITICAL
        ::= { IntelligentServerServerTRAPObject 655624 }
 
 -- Cooling Device speed has increased above Upper critical threshold 
     IntelligentServerCoolingDeviceOverSpeedCriticalHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Over Speed problem (Upper critical, going high)" 
        --#SEVERITY CRITICAL
        ::= 655625
    IntelligentServerCoolingDeviceOverSpeedCriticalHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Over Speed problem (Upper critical, going high)" 
        --#SEVERITY CRITICAL
        ::= { IntelligentServerServerTRAPObject 655625 }
 
 -- Cooling Device speed has decreased below Upper non-recoverable threshold 
     IntelligentServerCoolingDeviceOverSpeedNonRecoverableLow TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Over Speed problem (Upper non-recoverable, going low)" 
        --#SEVERITY CRITICAL
        ::= 655626
    IntelligentServerCoolingDeviceOverSpeedNonRecoverableLow-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Over Speed problem (Upper non-recoverable, going low)" 
        --#SEVERITY CRITICAL
        ::= { IntelligentServerServerTRAPObject 655626 }
 
-- Cooling Device speed has increased above Upper non-recoverable threshold 
    IntelligentServerCoolingDeviceOverSpeedNonRecoverableHigh TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Cooling Device Over Speed problem (Upper non-recoverable, going high)"
        --#SEVERITY CRITICAL
        ::= 655627
    IntelligentServerCoolingDeviceOverSpeedNonRecoverableHigh-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Cooling Device Over Speed problem (Upper non-recoverable, going high)"
        --#SEVERITY CRITICAL
        ::= { IntelligentServerServerTRAPObject 655627 }
 
-- Cooling Device speed decreased below lower non-critical threshold Cleared 
    IntelligentServerCoolingDeviceUnderSpeedWarningLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cooling Device Under Speed Warning (Lower non-critical, going low) Cleared"
        --#SEVERITY INFORMATION
        ::= 655744
    IntelligentServerCoolingDeviceUnderSpeedWarningLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cooling Device Under Speed Warning (Lower non-critical, going low) Cleared"
        --#SEVERITY INFORMATION
        ::= { IntelligentServerServerTRAPObject 655744 }
 
-- Cooling Device speed increased above lower non-critical threshold Cleared 
    IntelligentServerCoolingDeviceUnderSpeedWarningHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cooling Device Under Speed Warning (Lower non-critical, going high) Cleared" 
        --#SEVERITY INFORMATION
        ::= 655745
    IntelligentServerCoolingDeviceUnderSpeedWarningHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cooling Device Under Speed Warning (Lower non-critical, going high) Cleared" 
        --#SEVERITY INFORMATION
        ::= { IntelligentServerServerTRAPObject 655745 }
 
-- Cooling Device speed decreased below lower critical threshold Cleared 
    IntelligentServerCoolingDeviceUnderSpeedCriticalLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Under Speed problem (Lower critical, going low) Cleared" 
        --#SEVERITY INFORMATION
        ::= 655746
    IntelligentServerCoolingDeviceUnderSpeedCriticalLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Under Speed problem (Lower critical, going low) Cleared" 
        --#SEVERITY INFORMATION
        ::= { IntelligentServerServerTRAPObject 655746 }
 
 -- Cooling Device speed increased above lower critical threshold Cleared 
     IntelligentServerCoolingDeviceUnderSpeedCriticalHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Under Speed problem (Lower critical, going high) Cleared" 
        --#SEVERITY INFORMATION
        ::= 655747
    IntelligentServerCoolingDeviceUnderSpeedCriticalHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Under Speed problem (Lower critical, going high) Cleared" 
        --#SEVERITY INFORMATION
        ::= { IntelligentServerServerTRAPObject 655747 }
 
 -- Cooling Device speed decreased below lower non-recoverable threshold Cleared 
     IntelligentServerCoolingDeviceUnderSpeedNonRecoverableLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Under Speed problem (Lower non-recoverable, going low) Cleared" 
        --#SEVERITY INFORMATION
        ::= 655748
    IntelligentServerCoolingDeviceUnderSpeedNonRecoverableLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Under Speed problem (Lower non-recoverable, going low) Cleared" 
        --#SEVERITY INFORMATION
        ::= { IntelligentServerServerTRAPObject 655748 }
 
-- Cooling Device speed increased above lower non-recoverable threshold Cleared 
    IntelligentServerCoolingDeviceUnderSpeedNonRecoverableHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Cooling Device Under Speed problem (Lower non-recoverable, going high) Cleared" 
        --#SEVERITY INFORMATION
        ::= 655749
    IntelligentServerCoolingDeviceUnderSpeedNonRecoverableHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Cooling Device Under Speed problem (Lower non-recoverable, going high) Cleared" 
        --#SEVERITY INFORMATION
        ::= { IntelligentServerServerTRAPObject 655749 }
 
-- Cooling Device speed decreased below Upper non-critical threshold Cleared 
    IntelligentServerCoolingDeviceOverSpeedWarningLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cooling Device Over Speed Warning (Upper non-critical, going low) Cleared" 
        --#SEVERITY INFORMATION
        ::= 655750
    IntelligentServerCoolingDeviceOverSpeedWarningLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cooling Device Over Speed Warning (Upper non-critical, going low) Cleared" 
        --#SEVERITY INFORMATION
        ::= { IntelligentServerServerTRAPObject 655750 }
 
-- Cooling Device speed increased above upper non-critical threshold Cleared 
    IntelligentServerCoolingDeviceOverSpeedWarningHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Cooling Device Over Speed Warning (Upper non-critical, going high)Cleared" 
        --#SEVERITY INFORMATION
        ::= 655751
    IntelligentServerCoolingDeviceOverSpeedWarningHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Cooling Device Over Speed Warning (Upper non-critical, going high)Cleared" 
        --#SEVERITY INFORMATION
        ::= { IntelligentServerServerTRAPObject 655751 }
 
-- Cooling Device speed decreased below Upper critical threshold Cleared 
    IntelligentServerCoolingDeviceOverSpeedCriticalLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Over Speed problem (Upper critical, going low) Cleared"
        --#SEVERITY INFORMATION
        ::= 655752
    IntelligentServerCoolingDeviceOverSpeedCriticalLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Over Speed problem (Upper critical, going low) Cleared"
        --#SEVERITY INFORMATION
        ::= { IntelligentServerServerTRAPObject 655752 }
 
 -- Cooling Device speed increased above Upper critical threshold Cleared 
     IntelligentServerCoolingDeviceOverSpeedCriticalHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Over Speed problem (Upper critical, going high) Cleared"
        --#SEVERITY INFORMATION
        ::= 655753
    IntelligentServerCoolingDeviceOverSpeedCriticalHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Over Speed problem (Upper critical, going high) Cleared"
        --#SEVERITY INFORMATION
        ::= { IntelligentServerServerTRAPObject 655753 }
 
 -- Cooling Device speed decreased below Upper non-recoverable threshold Cleared 
     IntelligentServerCoolingDeviceOverSpeedNonRecoverableLowCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Over Speed problem (Upper non-recoverable, going low)Cleared" 
        --#SEVERITY INFORMATION
        ::= 655754
    IntelligentServerCoolingDeviceOverSpeedNonRecoverableLowCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Over Speed problem (Upper non-recoverable, going low)Cleared" 
        --#SEVERITY INFORMATION
        ::= { IntelligentServerServerTRAPObject 655754 }
 
-- Cooling Device speed increased above Upper non-recoverable threshold Cleared 
    IntelligentServerCoolingDeviceOverSpeedNonRecoverableHighCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Cooling Device Over Speed problem (Upper non-recoverable, going high) Cleared" 
        --#SEVERITY INFORMATION
        ::= 655755
    IntelligentServerCoolingDeviceOverSpeedNonRecoverableHighCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Cooling Device Over Speed problem (Upper non-recoverable, going high) Cleared" 
        --#SEVERITY INFORMATION
        ::= { IntelligentServerServerTRAPObject 655755 }
 
 -- Cooling Device Removed/Absent 
     IntelligentServerCoolingDeviceRemoved TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Cooling Device Removed/Absent"
        --#SEVERITY CRITICAL
        ::= 657408
    IntelligentServerCoolingDeviceRemoved-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Cooling Device Removed/Absent"
        --#SEVERITY CRITICAL
        ::= { IntelligentServerServerTRAPObject 657408 }
 
-- Cooling Device Inserted/Present 
    IntelligentServerCoolingDeviceInserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cooling Device Inserted/Present" 
        --#SEVERITY INFORMATION
        ::= 657409
    IntelligentServerCoolingDeviceInserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cooling Device Inserted/Present" 
        --#SEVERITY INFORMATION
        ::= { IntelligentServerServerTRAPObject 657409 }
 
-- Cooling Device Full Redundancy  
    IntelligentServerCoolingDeviceFullRedundancy TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Cooling Device redundancy has returned to Normal" 
        --#SEVERITY INFORMATION
        ::= 658176
    IntelligentServerCoolingDeviceFullRedundancy-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Cooling Device redundancy has returned to Normal" 
        --#SEVERITY INFORMATION
        ::= { IntelligentServerServerTRAPObject 658176 }

-- Cooling Device Redundancy lost  
    IntelligentServerCoolingDeviceRedundancyLost TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cooling Device Redundancy has been Lost" 
        --#SEVERITY CRITICAL
        ::= 658177
    IntelligentServerCoolingDeviceRedundancyLost-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cooling Device Redundancy has been Lost" 
        --#SEVERITY CRITICAL
        ::= { IntelligentServerServerTRAPObject 658177 }

-- Cooling Device Redundancy degraded 
    IntelligentServerCoolingDeviceRedundancyDegraded TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cooling Device Redundancy is in a degraded state"
        --#SEVERITY WARNING
        ::= 658178
    IntelligentServerCoolingDeviceRedundancyDegraded-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cooling Device Redundancy is in a degraded state"
        --#SEVERITY WARNING
        ::= { IntelligentServerServerTRAPObject 658178 }

-- CPU Cooling Liquid Leakage  
    IntelligentServerCoolingLiquidLeakagePoweroff TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU Cooling Liquid Leakage " 
        --#SEVERITY CRITICAL
        ::= 683781
    IntelligentServerCoolingLiquidLeakagePoweroff-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU Cooling Liquid Leakage " 
	    --#SEVERITY CRITICAL
        ::= { IntelligentServerServerTRAPObject 683781 }

-- GPU Cooling Liquid Leakage
    IntelligentServerCoolingLiquidLeakagePoweroff TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "GPU Cooling Liquid Leakage " 
	    --#SEVERITY CRITICAL
        ::= 683782
    IntelligentServerCoolingLiquidLeakagePoweroff-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "GPU Cooling Liquid Leakage " 
	    --#SEVERITY CRITICAL
        ::= { IntelligentServerServerTRAPObject 683782 }        

-- CPU Cooling Liquid Leakage Line Not Present
    IntelligentServerCoolingLiquidLeakageLineselftestfaild TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU Cooling Liquid Leakage Line Not Present" 
        --#SEVERITY CRITICAL
        ::= 683779
    IntelligentServerCoolingLiquidLeakageLineselftestfaild-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU Cooling Liquid Leakage Line Not Present" 
	    --#SEVERITY CRITICAL
        ::= { IntelligentServerServerTRAPObject 683779 }

-- GPU Cooling Liquid Leakage Line Not Present 
    IntelligentServerCoolingLiquidLeakagePoweroff TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "GPU Cooling Liquid Leakage Line Not Present " 
        --#SEVERITY CRITICAL            
        ::= 683780
    IntelligentServerCoolingLiquidLeakagePoweroff-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "GPU Cooling Liquid Leakage Line Not Present " 
	    --#SEVERITY CRITICAL
        ::= { IntelligentServerServerTRAPObject 683780 }

-- Leakage Detect simulation test failed 
    IntelligentServerCoolingLiquidLeakagePoweroff TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Leakage Detect simulation test failed " 
        --#SEVERITY CRITICAL            
        ::= 683778
    IntelligentServerCoolingLiquidLeakagePoweroff-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Leakage Detect simulation test failed " 
	    --#SEVERITY CRITICAL            
        ::= { IntelligentServerServerTRAPObject 683778 }
-- ********************************************** 
-- *        Memory          * 
-- ********************************************** 

-- Memory VR Failure state has been cleared 
    IntelligentServerMemoryVRFailureDeasserted TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory VR Failure state has been cleared"
        --#SEVERITY INFORMATION
        ::= 787200
    IntelligentServerMemoryVRFailureDeasserted-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory VR Failure state has been cleared"
        --#SEVERITY INFORMATION
        ::= { IntelligentServerServerTRAPObject 787200 }

-- Memory VR Failure state has been asserted 
    IntelligentServerMemoryVRFailureAsserted TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory VR Failure state has been asserted"
        --#SEVERITY CRITICAL
        ::= 787201
    IntelligentServerMemoryVRFailureAsserted-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory VR Failure state has been asserted"
        --#SEVERITY CRITICAL
        ::= { IntelligentServerServerTRAPObject 787201 }

-- Memory Predictive Failure state has been cleared 
    IntelligentServerMemoryPredictiveFailureDeasserted TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory Predictive Failure state has been cleared" 
        --#SEVERITY INFORMATION
        ::= 787456
    IntelligentServerMemoryPredictiveFailureDeasserted-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory Predictive Failure state has been cleared" 
        --#SEVERITY INFORMATION
        ::= { IntelligentServerServerTRAPObject 787456 }
 
-- Memory Predictive Failure state has been asserted 
    IntelligentServerMemoryPredictiveFailureAsserted TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current 
        ENTERPRISE IntelligentServerServerTRAPObject
        DESCRIPTION
            "Memory Predictive Failure state has been asserted"
        --#SEVERITY CRITICAL
        ::= 787457
    IntelligentServerMemoryPredictiveFailureAsserted-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Memory Predictive Failure state has been asserted"
        --#SEVERITY CRITICAL
        ::= { IntelligentServerServerTRAPObject 787457 }

-- Memory Uncorrectable ECC or other uncorrectable memory error
    IntelligentServerMemoryUncorrectableECCOrOtherError TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current 
        ENTERPRISE IntelligentServerServerTRAPObject
        DESCRIPTION
            "Memory Uncorrectable ECC or other uncorrectable memory error"
        --#SEVERITY CRITICAL
        ::= 789505
    IntelligentServerMemoryUncorrectableECCOrOtherError-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Memory Uncorrectable ECC or other uncorrectable memory error"
        --#SEVERITY CRITICAL
        ::= { IntelligentServerServerTRAPObject 789505 }

-- Memory Pin Out Memhot
    IntelligentServerMemoryPinOutMemhot TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current 
        ENTERPRISE IntelligentServerServerTRAPObject
        DESCRIPTION
            "Memory Pin Out Memhot"
        --#SEVERITY CRITICAL
        ::= 789553
    IntelligentServerMemoryPinOutMemhot-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Memory Pin Out Memhot"
        --#SEVERITY CRITICAL
        ::= { IntelligentServerServerTRAPObject 789553 }

-- Correctable ECC or other correctable memory error detected. 
    IntelligentServerMemoryCorrectableEccError TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Correctable ECC or other correctable memory error detected." 
        --#SEVERITY WARNING
        ::= 814848
    IntelligentServerMemoryCorrectableEccError-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Correctable ECC or other correctable memory error detected." 
        --#SEVERITY WARNING
        ::= { IntelligentServerServerTRAPObject 814848 }
 
-- Uncorrectable ECC or other uncorrectable memory error detected 
    IntelligentServerMemoryUncorrectableEccError TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Uncorrectable ECC or other uncorrectable memory error detected." 
        --#SEVERITY CRITICAL
        ::= 814849
    IntelligentServerMemoryUncorrectableEccError-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Uncorrectable ECC or other uncorrectable memory error detected." 
        --#SEVERITY CRITICAL
        ::= { IntelligentServerServerTRAPObject 814849 }

 -- Parity error detected. 
     IntelligentServerMemoryParityError TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Parity error detected." 
        --#SEVERITY WARNING
        ::= 814850
    IntelligentServerMemoryParityError-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Parity error detected." 
        --#SEVERITY WARNING
        ::= { IntelligentServerServerTRAPObject 814850 }
 
-- Memory Scrub Failed 
    IntelligentServerMemoryScrubFailed TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory Scrub Failed" 
        --#SEVERITY WARNING
        ::= 814851
    IntelligentServerMemoryScrubFailed-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory Scrub Failed" 
        --#SEVERITY WARNING
        ::= { IntelligentServerServerTRAPObject 814851 }
 
-- Memory Device Disabled 
    IntelligentServerMemoryDeviceDisabled TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory Device Disabled." 
        --#SEVERITY WARNING
        ::= 814852
    IntelligentServerMemoryDeviceDisabled-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory Device Disabled." 
        --#SEVERITY WARNING
        ::= { IntelligentServerServerTRAPObject 814852 }
 
-- Correctable ECC / other correctable memory error logging limit reached 
    IntelligentServerMemoryCorrectableECC TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Correctable ECC / other correctable memory error logging limit reached"
        --#SEVERITY CRITICAL
        ::= 814853
    IntelligentServerMemoryCorrectableECC-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Correctable ECC / other correctable memory error logging limit reached"
        --#SEVERITY CRITICAL
        ::= { IntelligentServerServerTRAPObject 814853 }
 
-- Memory Presence detected 
    IntelligentServerMemoryPresenceDetectedAssert TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory Presence detected."
        --#SEVERITY INFORMATION
        ::= 814854
    IntelligentServerMemoryPresenceDetectedAssert-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory Presence detected."
        --#SEVERITY INFORMATION
        ::= { IntelligentServerServerTRAPObject 814854 }
 
 -- Configuration Error 
     IntelligentServerMemoryConfigurationError TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory Configuration Error detected."
        --#SEVERITY CRITICAL
        ::= 814855
    IntelligentServerMemoryConfigurationError-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory Configuration Error detected."
        --#SEVERITY CRITICAL
        ::= { IntelligentServerServerTRAPObject 814855 }
 
-- Spare Unit of Memory detected 
    IntelligentServerMemorySpareUnit TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Spare Unit of Memory detected"
        --#SEVERITY INFORMATION
        ::= 814856
    IntelligentServerMemorySpareUnit-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Spare Unit of Memory detected"
        --#SEVERITY INFORMATION
        ::= { IntelligentServerServerTRAPObject 814856 }
 
-- Memory Automatically Throttled 
    IntelligentServerMemoryAutomaticallyThrottled TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory Automatically Throttled" 
        --#SEVERITY WARNING
        ::= 814857
    IntelligentServerMemoryAutomaticallyThrottled-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory Automatically Throttled" 
        --#SEVERITY WARNING
        ::= { IntelligentServerServerTRAPObject 814857 }
 
-- Critical Overtemperature 
    IntelligentServerMemoryCriticalOvertemperature TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory event - Critical Overtemperature"
        --#SEVERITY CRITICAL
        ::= 814858
    IntelligentServerMemoryCriticalOvertemperature-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory event - Critical Overtemperature"
        --#SEVERITY CRITICAL
        ::= { IntelligentServerServerTRAPObject 814858 }
 
-- Correctable ECC or other correctable memory error cleared. 
    IntelligentServerMemoryCorrectableEccErrorCleared TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Correctable ECC or other correctable memory error cleared."
        --#SEVERITY INFORMATION
        ::= 814976
    IntelligentServerMemoryCorrectableEccErrorCleared-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Correctable ECC or other correctable memory error cleared."
        --#SEVERITY INFORMATION
        ::= { IntelligentServerServerTRAPObject 814976 }
 
-- Uncorrectable ECC or other uncorrectable memory error cleared 
    IntelligentServerMemoryUncorrectableEccErrorCleared TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Uncorrectable ECC or other uncorrectable memory error Cleared." 
        --#SEVERITY INFORMATION
        ::= 814977
    IntelligentServerMemoryUncorrectableEccErrorCleared-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Uncorrectable ECC or other uncorrectable memory error Cleared." 
        --#SEVERITY INFORMATION
        ::= { IntelligentServerServerTRAPObject 814977 }

 -- Parity error Cleared. 
     IntelligentServerMemoryParityErrorCleared TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Parity error Cleared." 
        --#SEVERITY INFORMATION
        ::= 814978
    IntelligentServerMemoryParityErrorCleared-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Parity error Cleared." 
        --#SEVERITY INFORMATION
        ::= { IntelligentServerServerTRAPObject 814978 }

-- Memory Scrub Failure Cleared 
    IntelligentServerMemoryScrubFailureCleared TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory Scrub Failure Cleared"
        --#SEVERITY INFORMATION
        ::= 814979
    IntelligentServerMemoryScrubFailureCleared-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory Scrub Failure Cleared"
        --#SEVERITY INFORMATION
        ::= { IntelligentServerServerTRAPObject 814979 }

-- Memory Device Enabled 
    IntelligentServerMemoryDeviceEnabled TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory Device Enabled."
        --#SEVERITY INFORMATION
        ::= 814980
    IntelligentServerMemoryDeviceEnabled-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory Device Enabled."
        --#SEVERITY INFORMATION
        ::= { IntelligentServerServerTRAPObject 814980 }
 
 -- Correctable ECC / other correctable memory error logging limit reached Cleared 
     IntelligentServerMemoryCorrectableECCCleared TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current 
        ENTERPRISE IntelligentServerServerTRAPObject
        DESCRIPTION
            "Correctable ECC / other correctable memory error logging limit reached Cleared"
        --#SEVERITY INFORMATION
        ::= 814981
    IntelligentServerMemoryCorrectableECCCleared-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Correctable ECC / other correctable memory error logging limit reached Cleared"
        --#SEVERITY INFORMATION
        ::= { IntelligentServerServerTRAPObject 814981 }

-- Memory Presence detected Deassert 
    IntelligentServerMemoryPresenceNotDetected TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory Presence Not detected"
        --#SEVERITY INFORMATION
        ::= 814982
    IntelligentServerMemoryPresenceNotDetected-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory Presence Not detected"
        --#SEVERITY INFORMATION
        ::= { IntelligentServerServerTRAPObject 814982 }
 
 -- Configuration Error Cleared 
     IntelligentServerMemoryConfigurationErrorCleared TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory Configuration Error Cleared."
        --#SEVERITY INFORMATION
        ::= 814983
    IntelligentServerMemoryConfigurationErrorCleared-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory Configuration Error Cleared."
        --#SEVERITY INFORMATION
        ::= { IntelligentServerServerTRAPObject 814983 }

-- Spare Unit of Memory detected Deassert 
    IntelligentServerMemorySpareUnitDeassert TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Spare Unit of Memory detected Deassert" 
        --#SEVERITY INFORMATION
        ::= 814984
    IntelligentServerMemorySpareUnitDeassert-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Spare Unit of Memory detected Deassert" 
        --#SEVERITY INFORMATION
        ::= { IntelligentServerServerTRAPObject 814984 }

-- Memory Automatically Throttled Cleared 
    IntelligentServerMemoryAutomaticallyThrottledCleared TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory Automatically Throttled Cleared" 
        --#SEVERITY INFORMATION
        ::= 814985
    IntelligentServerMemoryAutomaticallyThrottledCleared-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory Automatically Throttled Cleared" 
        --#SEVERITY INFORMATION
        ::= { IntelligentServerServerTRAPObject 814985 }

-- Critical Overtemperature Cleared 
    IntelligentServerMemoryCriticalOvertemperatureCleared TRAP-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Memory event - Critical Overtemperature Cleared"  
        --#SEVERITY INFORMATION
        ::= 814986
    IntelligentServerMemoryCriticalOvertemperatureCleared-V2cV3 NOTIFICATION-TYPE 
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Memory event - Critical Overtemperature Cleared"  
        --#SEVERITY INFORMATION
        ::= { IntelligentServerServerTRAPObject 814986 }

-- ********************************************** 
-- *        Drive Slot (Bay)            * 
-- ********************************************** 
-- Hard Disk Drive Fault Sensor event 
    IntelligentServerDriveSlotPredictiveFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert } 
        STATUS current
        ENTERPRISE IntelligentServerServerTRAPObject
        DESCRIPTION
            "This state indicates that a HDD Fault LED which was ON before is OFF now."
        --#SEVERITY  INFORMATION
        ::= 852992
    IntelligentServerDriveSlotPredictiveFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert } 
        STATUS current
        DESCRIPTION
            "This state indicates that a HDD Fault LED which was ON before is OFF now."
        --#SEVERITY  INFORMATION
        ::= { IntelligentServerServerTRAPObject 852992 }

-- Hard Disk Drive Fault Sensor event 
    IntelligentServerDriveSlotPredictiveFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "A HDD Fault LED is ON."
        --#SEVERITY WARNING
        ::= 852993
    IntelligentServerDriveSlotPredictiveFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "A HDD Fault LED is ON."
        --#SEVERITY WARNING
        ::= { IntelligentServerServerTRAPObject 852993 }

-- Hard Disk Drive Presence Sensor event 
    IntelligentServerDriveSlotDriveRemovedOrAbsent TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive is absent or has been removed."
        --#SEVERITY INFORMATION
        ::= 880512
        -- Change from 880384 to 880512 for Insert Alert Absent, Remove Alert Present 20141010<<>>
    IntelligentServerDriveSlotDriveRemovedOrAbsent-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive is absent or has been removed."
        --#SEVERITY INFORMATION
        ::= { IntelligentServerServerTRAPObject 880512 }
        -- Change from 880384 to 880512 for Insert Alert Absent, Remove Alert Present 20141010<<>>
 
-- Hard Disk Drive Fault 
    IntelligentServerDriveSlotDriveFault TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive Fault"
        --#SEVERITY CRITICAL
        ::= 880385
    IntelligentServerDriveSlotDriveFault-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive Fault"
        --#SEVERITY CRITICAL
        ::= { IntelligentServerServerTRAPObject 880385 }

-- Hard Disk Drive Predictive Failure 
    IntelligentServerDriveSlotPredictiveFailure TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive Predictive Failure"
        --#SEVERITY WARNING
        ::= 880386
    IntelligentServerDriveSlotPredictiveFailure-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive Predictive Failure"
        --#SEVERITY WARNING
        ::= { IntelligentServerServerTRAPObject 880386 }

-- Hard Disk Drive Hot Spare (Ready to Remove) 
    IntelligentServerDriveSlotHotSpare TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
          " Hard Disk Drive Hot Spare (Ready to remove) Asserted "
        --#SEVERITY   INFORMATION
        ::= 880387
    IntelligentServerDriveSlotHotSpare-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
          " Hard Disk Drive Hot Spare (Ready to remove) Asserted "
        --#SEVERITY   INFORMATION
        ::= { IntelligentServerServerTRAPObject 880387 }

-- Hard Disk Drive Consistency Check / Parity Check in progress 
    IntelligentServerDriveSlotConsistencyCheckInProgress TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive Consistency Check / Parity Check in progress"
        --#SEVERITY   INFORMATION
        ::= 880388
    IntelligentServerDriveSlotConsistencyCheckInProgress-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive Consistency Check / Parity Check in progress"
        --#SEVERITY   INFORMATION
        ::= { IntelligentServerServerTRAPObject 880388 }

-- Hard Disk Drive In Critical Array 
    IntelligentServerDriveSlotInCriticalArray TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive In Critical Array"
        --#SEVERITY   INFORMATION
        ::= 880389
    IntelligentServerDriveSlotInCriticalArray-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive In Critical Array"
        --#SEVERITY   INFORMATION
        ::= { IntelligentServerServerTRAPObject 880389 }

-- Hard Disk Drive In Failed Array 
    IntelligentServerDriveSlotInFailedArray TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive In Failed Array"
        --#SEVERITY   CRITICAL
        ::= 880390
    IntelligentServerDriveSlotInFailedArray-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive In Failed Array"
        --#SEVERITY   CRITICAL
        ::= { IntelligentServerServerTRAPObject 880390 }

-- Hard Disk Drive Rebuild/Remap in progress 
    IntelligentServerDriveSlotRebuildOrRemapInProgress TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive Rebuild/Remap in progress"
        --#SEVERITY   INFORMATION
        ::= 880391
    IntelligentServerDriveSlotRebuildOrRemapInProgress-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive Rebuild/Remap in progress"
        --#SEVERITY   INFORMATION
        ::= { IntelligentServerServerTRAPObject 880391 }

-- Hard Disk Drive Rebuild/Remap Aborted 
    IntelligentServerDriveSlotRebuildOrRemapAborted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive Rebuild/Remap Aborted"
        --#SEVERITY   INFORMATION
        ::= 880392
    IntelligentServerDriveSlotRebuildOrRemapAborted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive Rebuild/Remap Aborted"
        --#SEVERITY   INFORMATION
        ::= { IntelligentServerServerTRAPObject 880392 }

-- Drive Presence Sensor event 
    IntelligentServerDriveSlotDriveInsertedOrPresent TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Hard Disk Drive is present or has been inserted."
        --#SEVERITY   INFORMATION
        ::= 880384
        -- Change from 880512 to 880384 for Insert Alert Absent, Remove Alert Present 20141010<<>>
    IntelligentServerDriveSlotDriveInsertedOrPresent-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Hard Disk Drive is present or has been inserted."
        --#SEVERITY   INFORMATION
        ::= { IntelligentServerServerTRAPObject 880384 }
        -- Change from 880512 to 880384 for Insert Alert Absent, Remove Alert Present 20141010<<>>

-- Hard Disk Drive Fault Cleared 
    IntelligentServerDriveSlotDriveFaultCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive Fault Cleared"
        --#SEVERITY   INFORMATION
        ::= 880513
    IntelligentServerDriveSlotDriveFaultCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive Fault Cleared"
        --#SEVERITY   INFORMATION
        ::= { IntelligentServerServerTRAPObject 880513 }

-- Hard Disk Drive Predictive Failure Cleared 
    IntelligentServerDriveSlotPredictiveFailureCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive Predictive Failure Cleared"
        --#SEVERITY   INFORMATION
        ::= 880514
    IntelligentServerDriveSlotPredictiveFailureCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive Predictive Failure Cleared"
        --#SEVERITY   INFORMATION
        ::= { IntelligentServerServerTRAPObject 880514 }

-- Hard Disk Drive Hot Spare 
    IntelligentServerDriveSlotHotSpareDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive Hot Spare Deasserted"
        --#SEVERITY   INFORMATION
        ::= 880515
    IntelligentServerDriveSlotHotSpareDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive Hot Spare Deasserted"
        --#SEVERITY   INFORMATION
        ::= { IntelligentServerServerTRAPObject 880515 }

-- Hard Disk Drive Consistency Check / Parity Check in progress Deasserted 
    IntelligentServerDriveSlotConsistencyCheckInProgressDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive Consistency Check / Parity Check in progress Deasserted"
--#SEVERITY   INFORMATION
        ::= 880516
    IntelligentServerDriveSlotConsistencyCheckInProgressDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive Consistency Check / Parity Check in progress Deasserted"
        --#SEVERITY   INFORMATION
        ::= { IntelligentServerServerTRAPObject 880516 }

-- Hard Disk Drive In Critical Array Deasserted 
    IntelligentServerDriveSlotInCriticalArrayDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive In Critical Array Deasserted"
        --#SEVERITY   INFORMATION
        ::= 880517
    IntelligentServerDriveSlotInCriticalArrayDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive In Critical Array Deasserted"
        --#SEVERITY   INFORMATION
        ::= { IntelligentServerServerTRAPObject 880517 }

-- Hard Disk Drive In Failed Array Deasserted 
    IntelligentServerDriveSlotInFailedArrayDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive In Failed Array Deasserted"
        --#SEVERITY   INFORMATION
        ::= 880518
    IntelligentServerDriveSlotInFailedArrayDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive In Failed Array Deasserted"
        --#SEVERITY   INFORMATION
        ::= { IntelligentServerServerTRAPObject 880518 }

-- Hard Disk Drive Rebuild/Remap in progress Deasserted 
    IntelligentServerDriveSlotRebuildOrRemapInProgressDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive Rebuild/Remap in progress Deasserted(completed)" 
        --#SEVERITY   INFORMATION
        ::= 880519
    IntelligentServerDriveSlotRebuildOrRemapInProgressDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive Rebuild/Remap in progress Deasserted(completed)" 
        --#SEVERITY   INFORMATION
        ::= { IntelligentServerServerTRAPObject 880519 }

-- Hard Disk Drive Rebuild/Remap Aborted Deasserted(completed) 
    IntelligentServerDriveSlotRebuildOrRemapAbortedDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hard Disk Drive Rebuild/Remap Aborted Deasserted" 
        --#SEVERITY   INFORMATION
        ::= 880520
    IntelligentServerDriveSlotRebuildOrRemapAbortedDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hard Disk Drive Rebuild/Remap Aborted Deasserted" 
        --#SEVERITY   INFORMATION
        ::= { IntelligentServerServerTRAPObject 880520 }

-- ********************************************** 
-- *        POST Memory Resize          * 
-- ********************************************** 

-- POST Memory Resize Failure Deasserted 
    IntelligentServerPOSTMemoryResizeFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "POST Memory Resize Failure Deasserted" 
        --#SEVERITY INFORMATION
        ::= 918528
    IntelligentServerPOSTMemoryResizeFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "POST Memory Resize Failure Deasserted" 
        --#SEVERITY INFORMATION
        ::= { IntelligentServerServerTRAPObject 918528 }

-- POST Memory Resize Failure Asserted 
    IntelligentServerPOSTMemoryResizeFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "POST Memory Resize Failure Asserted" 
        --#SEVERITY   WARNING
        ::= 918529
    IntelligentServerPOSTMemoryResizeFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "POST Memory Resize Failure Asserted" 
        --#SEVERITY   WARNING
        ::= { IntelligentServerServerTRAPObject 918529 }

-- ********************************************** 
-- *        System Firmware Progress            * 
-- ********************************************** 
-- Power On Self Test (POST) code error 
    IntelligentServerBIOSPOSTCodeError TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Firmware Progress- BIOS POST code error"
        --#SEVERITY CRITICAL
        ::= 1011456
    IntelligentServerBIOSPOSTCodeError-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Firmware Progress- BIOS POST code error"
        --#SEVERITY CRITICAL
        ::= { IntelligentServerServerTRAPObject 1011456 }

-- System Firmware Hang 
    IntelligentServerSystemFirmwareHang TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Firmware Hang"
        --#SEVERITY CRITICAL
        ::= 1011457
    IntelligentServerSystemFirmwareHang-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Firmware Hang"
        --#SEVERITY CRITICAL
        ::= { IntelligentServerServerTRAPObject 1011457 }

-- System Firmware Progress 
    IntelligentServerSystemFirmwareProgress TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Firmware Progress" 
        --#SEVERITY INFORMATION
        ::= 1011458
    IntelligentServerSystemFirmwareProgress-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Firmware Progress" 
        --#SEVERITY INFORMATION
        ::= { IntelligentServerServerTRAPObject 1011458 }

-- Power On Self Test (POST) code error Cleared 
    IntelligentServerBIOSPOSTCodeErrorCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Firmware Progress- BIOS POST code error Cleared" 
        --#SEVERITY INFORMATION
        ::= 1011584
    IntelligentServerBIOSPOSTCodeErrorCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Firmware Progress- BIOS POST code error Cleared" 
        --#SEVERITY INFORMATION
        ::= { IntelligentServerServerTRAPObject 1011584 }

-- System Firmware Hang Cleared 
    IntelligentServerSystemFirmwareHangCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Firmware Hang Cleared" 
        --#SEVERITY INFORMATION
        ::= 1011585
    IntelligentServerSystemFirmwareHangCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Firmware Hang Cleared" 
        --#SEVERITY INFORMATION
        ::= { IntelligentServerServerTRAPObject 1011585 }

-- System Firmware Progress Completed  
    IntelligentServerSystemFirmwareProgressCompleted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Firmware Progress Completed " 
        --#SEVERITY INFORMATION
        ::= 1011586
    IntelligentServerSystemFirmwareProgressCompleted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Firmware Progress Completed " 
        --#SEVERITY INFORMATION
        ::= { IntelligentServerServerTRAPObject 1011586 }

-- ********************************************** 
-- *        Event Logging Disabled          * 
-- ********************************************** 

-- Correctable Memory Error Logging Disabled 
    IntelligentServerCorrectableMemoryErrorLoggingDisabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Correctable Memory Error Logging Disabled"
        --#SEVERITY INFORMATION
        ::= 1076992
    IntelligentServerCorrectableMemoryErrorLoggingDisabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Correctable Memory Error Logging Disabled"
        --#SEVERITY INFORMATION
        ::= { IntelligentServerServerTRAPObject 1076992 }

-- Event Type Logging Disabled. 
    IntelligentServerEventTypeLoggingDisabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Event Type Logging Disabled" 
        --#SEVERITY INFORMATION
        ::= 1076993
    IntelligentServerEventTypeLoggingDisabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Event Type Logging Disabled" 
        --#SEVERITY INFORMATION
        ::= { IntelligentServerServerTRAPObject 1076993 }

-- SEL Area Reset/Cleared 
    IntelligentServerSELAreaResetOrCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SEL Area Reset/Cleared"
        --#SEVERITY INFORMATION
        ::= 1076994
    IntelligentServerSELAreaResetOrCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SEL Area Reset/Cleared"
        --#SEVERITY INFORMATION
        ::= { IntelligentServerServerTRAPObject 1076994 }

-- All Event Logging Disabled 
    IntelligentServerEventLoggingDisabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Event Logging Disabled"
        --#SEVERITY CRITICAL
        ::= 1076995
    IntelligentServerEventLoggingDisabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Event Logging Disabled"
        --#SEVERITY CRITICAL
        ::= { IntelligentServerServerTRAPObject 1076995 }

-- SEL Full 
    IntelligentServerSelFull TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SEL Full."
        --#SEVERITY INFORMATION
        ::= 1076996
    IntelligentServerSelFull-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SEL Full."
        --#SEVERITY INFORMATION
        ::= { IntelligentServerServerTRAPObject 1076996 }

 -- SEL Almost Full 
     IntelligentServerSelAlmostFull TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SEL Almost Full."
        --#SEVERITY INFORMATION
        ::= 1076997
    IntelligentServerSelAlmostFull-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SEL Almost Full."
        --#SEVERITY INFORMATION
        ::= { IntelligentServerServerTRAPObject 1076997 }

-- Correctable Machine Check Error Logging Disabled 
    IntelligentServerCorrectableMachineCheckErrorLoggingDisabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Correctable Machine Check Error Logging Disabled"
        --#SEVERITY CRITICAL
        ::= 1076998 
    IntelligentServerCorrectableMachineCheckErrorLoggingDisabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Correctable Machine Check Error Logging Disabled"
        --#SEVERITY CRITICAL
        ::= { IntelligentServerServerTRAPObject 1076998  }

-- Correctable Memory Error Logging Enabled 
    IntelligentServerCorrectableMemoryErrorLoggingEnabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Correctable Memory Error Logging Enabled"
        --#SEVERITY INFORMATION
        ::= 1077120
    IntelligentServerCorrectableMemoryErrorLoggingEnabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Correctable Memory Error Logging Enabled"
        --#SEVERITY INFORMATION
        ::= { IntelligentServerServerTRAPObject 1077120 }

-- Event Type Logging Enabled. 
    IntelligentServerEventTypeLoggingEnabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Event Type Logging Enabled"
        --#SEVERITY INFORMATION
        ::= 1077121
    IntelligentServerEventTypeLoggingEnabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Event Type Logging Enabled"
        --#SEVERITY INFORMATION
        ::= { IntelligentServerServerTRAPObject 1077121 }

-- SEL Area Reset/Cleared Event Deasserted 
    IntelligentServerSELAreaResetOrClearedEventDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SEL Area Reset/Cleared"
        --#SEVERITY INFORMATION
        ::= 1077122
    IntelligentServerSELAreaResetOrClearedEventDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SEL Area Reset/Cleared"
        --#SEVERITY INFORMATION
        ::= { IntelligentServerServerTRAPObject 1077122 }

-- All Event Logging Enabled 
    IntelligentServerEventLoggingEnabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Event Logging Enabled"
        --#SEVERITY INFORMATION
        ::= 1077123
    IntelligentServerEventLoggingEnabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Event Logging Enabled"
        --#SEVERITY INFORMATION
        ::= { IntelligentServerServerTRAPObject 1077123 }

-- SEL Full Event Cleared 
    IntelligentServerSelFullEventCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SEL Full Event Cleared"
        --#SEVERITY INFORMATION
        ::= 1077124
    IntelligentServerSelFullEventCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SEL Full Event Cleared"
        --#SEVERITY INFORMATION
        ::= { IntelligentServerServerTRAPObject 1077124 }

 -- SEL Almost Full Event Cleared 
     IntelligentServerSelAlmostFullEventCleared TRAP-TYPE
        OBJECTS { altHostLocation, altTrapTime, altSysManufacture, altSysModel, altSensorName, altSensorType, altSensorReading, altSensorThreshold, altHostContact, altBMCHostName, altSysName, altSpTxtId, altPriority, altEventAssertOrDeassert } 
        STATUS current
        ENTERPRISE IntelligentServerServerTRAPObject
        DESCRIPTION
            "SEL Almost Full Event Cleared"
        --#SEVERITY INFORMATION
        ::= 1077125
    IntelligentServerSelAlmostFullEventCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert } 
        STATUS current
        DESCRIPTION
            "SEL Almost Full Event Cleared"
        --#SEVERITY INFORMATION
        ::= { IntelligentServerServerTRAPObject 1077125 }

-- Correctable Machine Check Error Logging Enabled 
    IntelligentServerCorrectableMachineCheckErrorLoggingEnabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Correctable Machine Check Error Logging Enabled"
        --#SEVERITY INFORMATION
        ::= 1077126
    IntelligentServerCorrectableMachineCheckErrorLoggingEnabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Correctable Machine Check Error Logging Enabled"
        --#SEVERITY INFORMATION
        ::= { IntelligentServerServerTRAPObject 1077126 }

-- ********************************************** 
-- *        WatchDog1           * 
-- ********************************************** 
-- BIOS Watchdog Reset 
    IntelligentServerBIOSWatchdogReset TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "BIOS Watchdog Reset" 
        --#SEVERITY INFORMATION
        ::= 1142528
    IntelligentServerBIOSWatchdogReset-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "BIOS Watchdog Reset" 
        --#SEVERITY INFORMATION
        ::= { IntelligentServerServerTRAPObject 1142528 }

-- OS Watchdog Reset 
    IntelligentServerOSWatchdogReset TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Watchdog Reset"
        --#SEVERITY INFORMATION
        ::= 1142529
    IntelligentServerOSWatchdogReset-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Watchdog Reset"
        --#SEVERITY INFORMATION
        ::= { IntelligentServerServerTRAPObject 1142529 }

-- OS Watchdog Shut Down 
    IntelligentServerOSWatchdogShutDown TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Watchdog Shut Down"
        --#SEVERITY INFORMATION
        ::= 1142530
    IntelligentServerOSWatchdogShutDown-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Watchdog Shut Down"
        --#SEVERITY INFORMATION
        ::= { IntelligentServerServerTRAPObject 1142530 }

-- OS Watchdog Power Down 
    IntelligentServerOSWatchdogPowerDown TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Watchdog Power Down"
        --#SEVERITY INFORMATION
        ::= 1142531
    IntelligentServerOSWatchdogPowerDown-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Watchdog Power Down"
        --#SEVERITY INFORMATION
        ::= { IntelligentServerServerTRAPObject 1142531 }

-- OS Watchdog Power Cycle 
    IntelligentServerOSWatchdogPowerCycle TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Watchdog Power Cycle"
        --#SEVERITY INFORMATION
        ::= 1142532
    IntelligentServerOSWatchdogPowerCycle-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Watchdog Power Cycle"
        --#SEVERITY INFORMATION
        ::= { IntelligentServerServerTRAPObject 1142532 }

-- OS Watchdog NMI / Diagnostic Interrupt 
    IntelligentServerOSWatchdogNMIOrDiagnosticInterrupt TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Watchdog NMI / Diagnostic Interrupt"
        --#SEVERITY CRITICAL
        ::= 1142533
    IntelligentServerOSWatchdogNMIOrDiagnosticInterrupt-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Watchdog NMI / Diagnostic Interrupt"
        --#SEVERITY CRITICAL
        ::= { IntelligentServerServerTRAPObject 1142533 }

-- OS Watchdog Expired, status only 
    IntelligentServerOSWatchdogExpired TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Watchdog Expired, status only"
        --#SEVERITY   INFORMATION
        ::= 1142534
    IntelligentServerOSWatchdogExpired-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Watchdog Expired, status only"
        --#SEVERITY   INFORMATION
        ::= { IntelligentServerServerTRAPObject 1142534 }

-- OS Watchdog pre-timeout Interrupt, non-NMI
    IntelligentServerOSWatchdogPreTimeoutInterrupt TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "OS Watchdog pre-timeout Interrupt, non-NMI"
        --#SEVERITY   INFORMATION
        ::= 1142535
    IntelligentServerOSWatchdogPreTimeoutInterrupt-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "OS Watchdog pre-timeout Interrupt, non-NMI"
        --#SEVERITY   INFORMATION
        ::= { IntelligentServerServerTRAPObject 1142535 }

-- BIOS Watchdog Reset Deasserted 
    IntelligentServerBIOSWatchdogResetDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "BIOS Watchdog Reset Deasserted"
        --#SEVERITY INFORMATION
        ::= 1142656
    IntelligentServerBIOSWatchdogResetDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "BIOS Watchdog Reset Deasserted"
        --#SEVERITY INFORMATION
        ::= { IntelligentServerServerTRAPObject 1142656 }

-- OS Watchdog Reset Deasserted
IntelligentServerOSWatchdogResetDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Watchdog Reset Deasserted"
        --#SEVERITY INFORMATION
        ::= 1142657
IntelligentServerOSWatchdogResetDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Watchdog Reset Deasserted"
        --#SEVERITY INFORMATION
        ::= { IntelligentServerServerTRAPObject 1142657 }

-- OS Watchdog Shut Down Deasserted 
    IntelligentServerOSWatchdogShutDownDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Watchdog Shut Down Deasserted"
        --#SEVERITY INFORMATION
        ::= 1142658
    IntelligentServerOSWatchdogShutDownDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Watchdog Shut Down Deasserted"
        --#SEVERITY INFORMATION
        ::= { IntelligentServerServerTRAPObject 1142658 }

-- OS Watchdog Power Down Deasserted 
    IntelligentServerOSWatchdogPowerDownDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "OS Watchdog Power Down Deasserted"
        --#SEVERITY INFORMATION
        ::= 1142659
    IntelligentServerOSWatchdogPowerDownDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "OS Watchdog Power Down Deasserted"
        --#SEVERITY INFORMATION
        ::= { IntelligentServerServerTRAPObject 1142659 }

-- OS Watchdog Power Cycle Deasserted 
    IntelligentServerOSWatchdogPowerCycleDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Watchdog Power Cycle Deasserted"
        --#SEVERITY INFORMATION
        ::= 1142660
    IntelligentServerOSWatchdogPowerCycleDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Watchdog Power Cycle Deasserted"
        --#SEVERITY INFORMATION
        ::= { IntelligentServerServerTRAPObject 1142660 }

-- OS Watchdog NMI / Diagnostic Interrupt Cleared 
    IntelligentServerOSWatchdogNMIOrDiagnosticInterruptCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Watchdog NMI / Diagnostic Interrupt Cleared"
        --#SEVERITY INFORMATION
        ::= 1142661
    IntelligentServerOSWatchdogNMIOrDiagnosticInterruptCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Watchdog NMI / Diagnostic Interrupt Cleared"
        --#SEVERITY INFORMATION
        ::= { IntelligentServerServerTRAPObject 1142661 }

-- OS Watchdog Expired, status only Event Cleared 
    IntelligentServerOSWatchdogExpiredEventCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Watchdog Expired, status only Event Cleared"
        --#SEVERITY INFORMATION
        ::= 1142662
    IntelligentServerOSWatchdogExpiredEventCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Watchdog Expired, status only Event Cleared"
        --#SEVERITY INFORMATION
        ::= { IntelligentServerServerTRAPObject 1142662 }

-- OS Watchdog pre-timeout Interrupt, (non-NMI) Cleared 
    IntelligentServerOSWatchdogPreTimeoutInterruptCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "OS Watchdog pre-timeout Interrupt Cleared"
        --#SEVERITY INFORMATION
        ::= 1142663 
    IntelligentServerOSWatchdogPreTimeoutInterruptCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "OS Watchdog pre-timeout Interrupt Cleared"
        --#SEVERITY INFORMATION
        ::= { IntelligentServerServerTRAPObject 1142663  }

-- ********************************************** 
-- *        System Event            * 
-- ********************************************** 

-- System Reconfigured 
    IntelligentServerSystemReconfigured TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Reconfigured"
        --#SEVERITY INFORMATION
        ::= 1208064
    IntelligentServerSystemReconfigured-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Reconfigured"
        --#SEVERITY INFORMATION
        ::= { IntelligentServerServerTRAPObject 1208064 }

-- OEM System Boot Event 
    IntelligentServerOEMSystemBootEvent TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OEM System Boot Event"
        --#SEVERITY WARNING
        ::= 1208065
    IntelligentServerOEMSystemBootEvent-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OEM System Boot Event"
        --#SEVERITY WARNING
        ::= { IntelligentServerServerTRAPObject 1208065 }

-- Undetermined system hardware failure 
    IntelligentServerUndeterminedSystemHardwareFailure TRAP-TYPE
        OBJECTS { altHostLocation, altTrapTime, altSysManufacture, altSysModel, altSensorName, altSensorType, altSensorReading, altSensorThreshold, altHostContact, altBMCHostName, altSysName, altSpTxtId, altPriority, altEventAssertOrDeassert } 
        STATUS current
        ENTERPRISE IntelligentServerServerTRAPObject
        DESCRIPTION
            "Undetermined system hardware failure"
        --#SEVERITY CRITICAL
        ::= 1208066
    IntelligentServerUndeterminedSystemHardwareFailure-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert } 
        STATUS current
        DESCRIPTION
            "Undetermined system hardware failure"
        --#SEVERITY CRITICAL
        ::= { IntelligentServerServerTRAPObject 1208066 }

-- SEL Entry added to Auxiliary Log 
    IntelligentServerEntryAddedToAuxiliaryLog TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SEL Entry added to Auxiliary Log"
        --#SEVERITY INFORMATION
        ::= 1208067
    IntelligentServerEntryAddedToAuxiliaryLog-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SEL Entry added to Auxiliary Log"
        --#SEVERITY INFORMATION
        ::= { IntelligentServerServerTRAPObject 1208067 }

-- PEF Action 
    IntelligentServerPEFAction TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "PEF Action is about to be taken. Event filters have been matched."
        --#SEVERITY INFORMATION
        ::= 1208068
    IntelligentServerPEFAction-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "PEF Action is about to be taken. Event filters have been matched."
        --#SEVERITY INFORMATION
        ::= { IntelligentServerServerTRAPObject 1208068 }

-- Timestamp Clock Synch 
    IntelligentServerTimestampClockSynch TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Timestamp Clock Synch"
        --#SEVERITY INFORMATION
        ::= 1208069 
    IntelligentServerTimestampClockSynch-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Timestamp Clock Synch"
        --#SEVERITY INFORMATION
        ::= { IntelligentServerServerTRAPObject 1208069  }

-- System Reconfigured Event Cleared 
    IntelligentServerSystemReconfiguredDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Reconfigured Event Cleared"
        --#SEVERITY INFORMATION
        ::= 1208192
    IntelligentServerSystemReconfiguredDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Reconfigured Event Cleared"
        --#SEVERITY INFORMATION
        ::= { IntelligentServerServerTRAPObject 1208192 }

-- OEM System Boot Event Cleared 
    IntelligentServerOEMSystemBootEventCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OEM System Boot Event Cleared"
        --#SEVERITY INFORMATION
        ::= 1208193
    IntelligentServerOEMSystemBootEventCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OEM System Boot Event Cleared"
        --#SEVERITY INFORMATION
        ::= { IntelligentServerServerTRAPObject 1208193 }

-- Undetermined system hardware failure Cleared 
    IntelligentServerUndeterminedSystemHardwareFailureCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Undetermined system hardware failure Cleared" 
        --#SEVERITY CRITICAL
        ::= 1208194
    IntelligentServerUndeterminedSystemHardwareFailureCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Undetermined system hardware failure Cleared" 
        --#SEVERITY CRITICAL
        ::= { IntelligentServerServerTRAPObject 1208194 }

-- SEL Entry added to Auxiliary Log Deasserted 
    IntelligentServerEntryAddedToAuxiliaryLogDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SEL Entry added to Auxiliary Log Deasserted"
        --#SEVERITY INFORMATION
        ::= 1208195
    IntelligentServerEntryAddedToAuxiliaryLogDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SEL Entry added to Auxiliary Log Deasserted"
        --#SEVERITY INFORMATION
        ::= { IntelligentServerServerTRAPObject 1208195 }

-- PEF Action Event Deasserted 
    IntelligentServerPEFActionEventDeassert TRAP-TYPE
    OBJECTS { altHostLocation, altTrapTime, altSysManufacture, altSysModel, altSensorName, altSensorType, altSensorReading, altSensorThreshold, altHostContact, altBMCHostName, altSysName, altSpTxtId, altPriority, altEventAssertOrDeassert }
    STATUS current
    ENTERPRISE IntelligentServerServerTRAPObject
    DESCRIPTION
        "PEF Action Event Deasserted"
        --#SEVERITY INFORMATION
    ::= 1208196
    IntelligentServerPEFActionEventDeassert-V2cV3 NOTIFICATION-TYPE
    OBJECTS { altHostLocation, altTrapTime, altSysManufacture, altSysModel, altSensorName, altSensorType, altSensorReading, altSensorThreshold, altHostContact, altBMCHostName, altSysName, altSpTxtId, altPriority, altEventAssertOrDeassert }
    STATUS current
    DESCRIPTION
        "PEF Action Event Deasserted"
        --#SEVERITY INFORMATION
    ::= { IntelligentServerServerTRAPObject 1208196 }

-- Timestamp Clock Synch Event Deasserted 
    IntelligentServerTimestampClockSynchEventDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Timestamp Clock Synch Event Deasserted"
        --#SEVERITY INFORMATION
        ::= 1208197 
    IntelligentServerTimestampClockSynchEventDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Timestamp Clock Synch Event Deasserted"
        --#SEVERITY INFORMATION
        ::= { IntelligentServerServerTRAPObject 1208197  }
  
-- ********************************************** 
-- *      Critical Interrupt          * 
-- ********************************************** 

-- Front Panel NMI / Diagnostic Interrupt 
    IntelligentServerCriticalInterruptFrontPanelNMI TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Front Panel NMI / Diagnostic Interrupt"
        --#SEVERITY CRITICAL
        ::= 1273600
    IntelligentServerCriticalInterruptFrontPanelNMI-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Front Panel NMI / Diagnostic Interrupt"
        --#SEVERITY CRITICAL
        ::= { IntelligentServerServerTRAPObject 1273600 }

-- Critical Interrupt, Bus timeout error 
    IntelligentServerCriticalInterruptBusTimeout TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, Bus Timeout error"
        --#SEVERITY CRITICAL
        ::= 1273601
    IntelligentServerCriticalInterruptBusTimeout-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, Bus Timeout error"
        --#SEVERITY CRITICAL
        ::= { IntelligentServerServerTRAPObject 1273601 }

-- Critical Interrupt, IO Channel Non-Maskable Interrupt 
    IntelligentServerCriticalInterruptIOChannelNMI TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, IO Channel check NMI error"
        --#SEVERITY CRITICAL
        ::= 1273602
    IntelligentServerCriticalInterruptIOChannelNMI-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, IO Channel check NMI error"
        --#SEVERITY CRITICAL
        ::= { IntelligentServerServerTRAPObject 1273602 }

-- Critical Interrupt, Software Non-Maskable Interrupt error 
    IntelligentServerCriticalInterruptSoftwareNMI TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Interrupt, software NMI error"
        --#SEVERITY CRITICAL
        ::= 1273603
    IntelligentServerCriticalInterruptSoftwareNMI-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Interrupt, software NMI error"
        --#SEVERITY CRITICAL
        ::= { IntelligentServerServerTRAPObject 1273603 }

-- Non special-cycle parity errors 
    IntelligentServerCriticalInterruptPCIPERR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Interrupt, PCI PERR parity error"
        --#SEVERITY CRITICAL
        ::= 1273604
    IntelligentServerCriticalInterruptPCIPERR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Interrupt, PCI PERR parity error"
        --#SEVERITY CRITICAL
        ::= { IntelligentServerServerTRAPObject 1273604 }

-- Special-cycle parity errors 
    IntelligentServerCriticalInterruptPCISERR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, PCI SERR parity error"
        --#SEVERITY CRITICAL
        ::= 1273605
    IntelligentServerCriticalInterruptPCISERR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, PCI SERR parity error"
        --#SEVERITY CRITICAL
        ::= { IntelligentServerServerTRAPObject 1273605 }

-- EISA Fail Safe Timeout 
    IntelligentServerCriticalInterruptEISAFailSafeTimeout TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, EISA Fail Safe Timeout"
        --#SEVERITY CRITICAL
        ::= 1273606
    IntelligentServerCriticalInterruptEISAFailSafeTimeout-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, EISA Fail Safe Timeout"
        --#SEVERITY CRITICAL
        ::= { IntelligentServerServerTRAPObject 1273606 }

-- Bus Correctable Error 
    IntelligentServerCriticalInterruptBusCorrectableError TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, Bus Correctable Error"
        --#SEVERITY CRITICAL
        ::= 1273607
    IntelligentServerCriticalInterruptBusCorrectableError-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, Bus Correctable Error"
        --#SEVERITY CRITICAL
        ::= { IntelligentServerServerTRAPObject 1273607 }

-- Bus uncorrectable error 
    IntelligentServerCriticalInterruptBusUncorrect TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, Bus Uncorrectable error"
        --#SEVERITY CRITICAL
        ::= 1273608
    IntelligentServerCriticalInterruptBusUncorrect-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, Bus Uncorrectable error"
        --#SEVERITY CRITICAL
        ::= { IntelligentServerServerTRAPObject 1273608 }

-- Fatal non-maskable interrupt (NMI) 
    IntelligentServerCriticalInterruptFatalNMI TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Interrupt, Fatal NMI error"
        --#SEVERITY CRITICAL
        ::= 1273609
    IntelligentServerCriticalInterruptFatalNMI-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Interrupt, Fatal NMI error"
        --#SEVERITY CRITICAL
        ::= { IntelligentServerServerTRAPObject 1273609 }

-- Bus Fatal Error 
    IntelligentServerCriticalInterruptFatalBusError TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Interrupt, Bus Fatal Error"
        --#SEVERITY CRITICAL
        ::= 1273610
    IntelligentServerCriticalInterruptFatalBusError-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Interrupt, Bus Fatal Error"
        --#SEVERITY CRITICAL
        ::= { IntelligentServerServerTRAPObject 1273610 }

-- Bus Degraded (bus operating in a degraded performance state) 
    IntelligentServerCriticalInterruptBusDegraded TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, Bus Degraded (bus operating in a degraded performance state)"
        --#SEVERITY CRITICAL
        ::= 1273611
    IntelligentServerCriticalInterruptBusDegraded-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, Bus Degraded (bus operating in a degraded performance state)"
        --#SEVERITY CRITICAL
        ::= { IntelligentServerServerTRAPObject 1273611 }

-- Front Panel NMI / Diagnostic Interrupt Cleared 
    IntelligentServerCriticalInterruptFrontPanelNMICleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Front Panel NMI / Diagnostic Interrupt Cleared"
        --#SEVERITY INFORMATION
        ::= 1273728
    IntelligentServerCriticalInterruptFrontPanelNMICleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Front Panel NMI / Diagnostic Interrupt Cleared"
        --#SEVERITY INFORMATION
        ::= { IntelligentServerServerTRAPObject 1273728 }

-- Critical Interrupt, Bus timeout error Cleared 
    IntelligentServerCriticalInterruptBusTimeoutCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, Bus Timeout error Cleared"
        --#SEVERITY INFORMATION
        ::= 1273729
    IntelligentServerCriticalInterruptBusTimeoutCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, Bus Timeout error Cleared"
        --#SEVERITY INFORMATION
        ::= { IntelligentServerServerTRAPObject 1273729 }

-- Critical Interrupt, IO Channel Non-Maskable Interrupt Cleared 
    IntelligentServerCriticalInterruptIOChannelNMICleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, IO Channel check NMI error Cleared"
        --#SEVERITY INFORMATION
        ::= 1273730
    IntelligentServerCriticalInterruptIOChannelNMICleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, IO Channel check NMI error Cleared"
        --#SEVERITY INFORMATION
        ::= { IntelligentServerServerTRAPObject 1273730 }

-- Critical Interrupt, Software Non-Maskable Interrupt error Cleared 
    IntelligentServerCriticalInterruptSoftwareNMICleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, software NMI error Cleared"
        --#SEVERITY INFORMATION
        ::= 1273731
    IntelligentServerCriticalInterruptSoftwareNMICleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, software NMI error Cleared"
        --#SEVERITY INFORMATION
        ::= { IntelligentServerServerTRAPObject 1273731 }

-- Non special-cycle parity errors Cleared 
    IntelligentServerCriticalInterruptPCIPERRCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, PCI PERR parity error Cleared"
        --#SEVERITY INFORMATION
        ::= 1273732
    IntelligentServerCriticalInterruptPCIPERRCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, PCI PERR parity error Cleared"
        --#SEVERITY INFORMATION
        ::= { IntelligentServerServerTRAPObject 1273732 }

-- Special-cycle parity errors Cleared 
    IntelligentServerCriticalInterruptPCISERRCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, PCI SERR parity error Cleared"
        --#SEVERITY INFORMATION
        ::= 1273733
    IntelligentServerCriticalInterruptPCISERRCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, PCI SERR parity error Cleared"
        --#SEVERITY INFORMATION
        ::= { IntelligentServerServerTRAPObject 1273733 }
  
-- EISA Fail Safe Timeout Event Cleared 
    IntelligentServerCriticalInterruptEISAFailSafeTimeoutCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, EISA Fail Safe Timeout Event Cleared"
        --#SEVERITY INFORMATION
        ::= 1273734
    IntelligentServerCriticalInterruptEISAFailSafeTimeoutCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, EISA Fail Safe Timeout Event Cleared"
        --#SEVERITY INFORMATION
        ::= { IntelligentServerServerTRAPObject 1273734 }

-- Bus Correctable Error Cleared
    IntelligentServerCriticalInterruptBusCorrectableErrorCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Critical Interrupt, Bus Correctable Error Cleared" 
        --#SEVERITY INFORMATION
        ::= 1273735
    IntelligentServerCriticalInterruptBusCorrectableErrorCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Critical Interrupt, Bus Correctable Error Cleared" 
        --#SEVERITY INFORMATION
        ::= { IntelligentServerServerTRAPObject 1273735 }

-- Bus uncorrectable error Cleared 
    IntelligentServerCriticalInterruptBusUncorrectCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, Bus Uncorrectable error Cleared"
        --#SEVERITY INFORMATION
        ::= 1273736
    IntelligentServerCriticalInterruptBusUncorrectCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, Bus Uncorrectable error Cleared"
        --#SEVERITY INFORMATION
        ::= { IntelligentServerServerTRAPObject 1273736 }

-- Fatal non-maskable interrupt (NMI) Cleared 
    IntelligentServerCriticalInterruptFatalNMICleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, Fatal NMI error Cleared" 
        --#SEVERITY INFORMATION
        ::= 1273737
    IntelligentServerCriticalInterruptFatalNMICleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, Fatal NMI error Cleared" 
        --#SEVERITY INFORMATION
        ::= { IntelligentServerServerTRAPObject 1273737 }
 
-- Bus Fatal Error Cleared 
    IntelligentServerCriticalInterruptFatalBusErrorCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, Bus Fatal Error Cleared" 
        --#SEVERITY INFORMATION
        ::= 1273738
    IntelligentServerCriticalInterruptFatalBusErrorCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, Bus Fatal Error Cleared" 
        --#SEVERITY INFORMATION
        ::= { IntelligentServerServerTRAPObject 1273738 }
 
-- Bus Degraded (bus operating in a degraded performance state) Event Cleared 
    IntelligentServerCriticalInterruptBusDegradedEventCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Critical Interrupt, Bus Degraded (bus operating in a degraded performance state) Event Cleared"  
        --#SEVERITY INFORMATION
        ::= 1273739
    IntelligentServerCriticalInterruptBusDegradedEventCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Critical Interrupt, Bus Degraded (bus operating in a degraded performance state) Event Cleared"  
        --#SEVERITY INFORMATION
        ::= { IntelligentServerServerTRAPObject 1273739 }
 
-- ********************************************** 
-- *        Button/Switch           * 
-- ********************************************** 

-- Power Button pressed 
    IntelligentServerPowerButtonPressed TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Button pressed."
        --#SEVERITY INFORMATION
        ::= 1339136
    IntelligentServerPowerButtonPressed-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Button pressed."
        --#SEVERITY INFORMATION
        ::= { IntelligentServerServerTRAPObject 1339136 }

-- Sleep Button pressed 
    IntelligentServerSleepButtonPressed TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Sleep Button pressed."
        --#SEVERITY INFORMATION
        ::= 1339137
    IntelligentServerSleepButtonPressed-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Sleep Button pressed."
        --#SEVERITY INFORMATION
        ::= { IntelligentServerServerTRAPObject 1339137 }

-- Reset Button pressed 
    IntelligentServerResetButtonPressed TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Reset Button pressed."
        --#SEVERITY INFORMATION
        ::= 1339138
    IntelligentServerResetButtonPressed-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Reset Button pressed."
        --#SEVERITY INFORMATION
        ::= { IntelligentServerServerTRAPObject 1339138 }

-- FRU latch open 
    IntelligentServerFRULatchOpen TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU latch open (Switch indicating FRU latch is in unlatched position and FRU is mechanically removable)" 
        --#SEVERITY INFORMATION
        ::= 1339139
    IntelligentServerFRULatchOpen-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU latch open (Switch indicating FRU latch is in unlatched position and FRU is mechanically removable)" 
        --#SEVERITY INFORMATION
        ::= { IntelligentServerServerTRAPObject 1339139 }

-- FRU service request button 
    IntelligentServerFRUServiceRequestButton TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU service request button"
        --#SEVERITY INFORMATION
        ::= 1339140
    IntelligentServerFRUServiceRequestButton-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU service request button"
        --#SEVERITY INFORMATION
        ::= { IntelligentServerServerTRAPObject 1339140 }

-- Power Button Released 
    IntelligentServerPowerButtonReleased TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Power Button Released."
        --#SEVERITY INFORMATION
        ::= 1339264
    IntelligentServerPowerButtonReleased-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Power Button Released."
        --#SEVERITY INFORMATION
        ::= { IntelligentServerServerTRAPObject 1339264 }

-- Sleep Button Released 
    IntelligentServerSleepButtonReleased TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Sleep Button Released."
        --#SEVERITY INFORMATION
        ::= 1339265
    IntelligentServerSleepButtonReleased-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Sleep Button Released."
        --#SEVERITY INFORMATION
        ::= { IntelligentServerServerTRAPObject 1339265 }

-- Reset Button Released 
    IntelligentServerResetButtonReleased TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Reset Button Released."
        --#SEVERITY INFORMATION
        ::= 1339266
    IntelligentServerResetButtonReleased-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Reset Button Released."
        --#SEVERITY INFORMATION
        ::= { IntelligentServerServerTRAPObject 1339266 }

-- FRU latch Closed 
    IntelligentServerFRULatchClosed TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU latch Closed (Switch indicating FRU latch is in latched position)"
        --#SEVERITY INFORMATION
        ::= 1339267
    IntelligentServerFRULatchClosed-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU latch Closed (Switch indicating FRU latch is in latched position)"
        --#SEVERITY INFORMATION
        ::= { IntelligentServerServerTRAPObject 1339267 }

-- FRU service request button Released 
    IntelligentServerFRUServiceRequestButtonReleased TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "FRU service request button Released"
        --#SEVERITY INFORMATION
        ::= 1339268
    IntelligentServerFRUServiceRequestButtonReleased-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "FRU service request button Released"
        --#SEVERITY INFORMATION
        ::= { IntelligentServerServerTRAPObject 1339268 }

-- ********************************************** 
-- *        Module/Board            * 
-- ********************************************** 
-- Module/Board State Deasserted 
    IntelligentServerBoardStateDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Module/Board State Deasserted"
        --#SEVERITY INFORMATION
        ::= 1377024
    IntelligentServerBoardStateDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Module/Board State Deasserted"
        --#SEVERITY INFORMATION
        ::= { IntelligentServerServerTRAPObject 1377024 }

-- Module/Board State Asserted 
    IntelligentServerBoardStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Module/Board State Asserted"
        --#SEVERITY INFORMATION
        ::= 1377025
    IntelligentServerBoardStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Module/Board State Asserted"
        --#SEVERITY INFORMATION
        ::= { IntelligentServerServerTRAPObject 1377025 }

-- Module/Board Predictive Failure Deasserted 
    IntelligentServerBoardPredictiveFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Module/Board Predictive Failure Deasserted"
        --#SEVERITY INFORMATION
        ::= 1377280
    IntelligentServerBoardPredictiveFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Module/Board Predictive Failure Deasserted"
        --#SEVERITY INFORMATION
        ::= { IntelligentServerServerTRAPObject 1377280 }

-- Module/Board Predictive Failure Asserted 
    IntelligentServerBoardPredictiveFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Module/Board Predictive Failure Asserted" 
        --#SEVERITY INFORMATION
        ::= 1377281
    IntelligentServerBoardPredictiveFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Module/Board Predictive Failure Asserted" 
        --#SEVERITY INFORMATION
        ::= { IntelligentServerServerTRAPObject 1377281 }

-- Module/Board Device Inserted Device Present
    IntelligentServerBoardDeviceInsertedDevicePresent TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Module/Board Device Inserted Device Present" 
        --#SEVERITY INFORMATION
        ::= 1378305
    IntelligentServerBoardDeviceInsertedDevicePresent-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Module/Board Device Inserted Device Present" 
        --#SEVERITY INFORMATION
        ::= { IntelligentServerServerTRAPObject 1378305 }

-- ********************************************** 
-- *        Microcontroller/Coprocessor         * 
-- ********************************************** 
-- Microcontroller/Coprocessor State Deasserted 
    IntelligentServerMicrocontrollerStateDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Microcontroller/Coprocessor State Deasserted" 
        --#SEVERITY INFORMATION
        ::= 1442560
    IntelligentServerMicrocontrollerStateDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Microcontroller/Coprocessor State Deasserted" 
        --#SEVERITY INFORMATION
        ::= { IntelligentServerServerTRAPObject 1442560 }

-- Microcontroller/Coprocessor State Asserted 
    IntelligentServerMicrocontrollerStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Microcontroller/Coprocessor State Asserted"
        --#SEVERITY INFORMATION
        ::= 1442561
    IntelligentServerMicrocontrollerStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Microcontroller/Coprocessor State Asserted"
        --#SEVERITY INFORMATION
        ::= { IntelligentServerServerTRAPObject 1442561 }

-- Microcontroller/Coprocessor Predictive Failure Deasserted 
    IntelligentServerMicrocontrollerPredictiveFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Microcontroller/Coprocessor Predictive Failure Deasserted"
        --#SEVERITY INFORMATION
        ::= 1442816

    IntelligentServerMicrocontrollerPredictiveFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Microcontroller/Coprocessor Predictive Failure Deasserted"
        --#SEVERITY INFORMATION
        ::= { IntelligentServerServerTRAPObject 1442816 }

-- Microcontroller/Coprocessor Predictive Failure Asserted 
    IntelligentServerMicrocontrollerPredictiveFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Microcontroller/Coprocessor Predictive Failure Asserted" 
        --#SEVERITY INFORMATION
        ::= 1442817
    IntelligentServerMicrocontrollerPredictiveFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Microcontroller/Coprocessor Predictive Failure Asserted" 
        --#SEVERITY INFORMATION
        ::= { IntelligentServerServerTRAPObject 1442817 }

--  Microcontroller/Coprocessor Device Disabled 
    IntelligentServerMicrocontrollerDeviceDisabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Microcontroller/Coprocessor Device Disabled" 
        --#SEVERITY WARNING
        ::= 1444096
    IntelligentServerMicrocontrollerDeviceDisabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Microcontroller/Coprocessor Device Disabled" 
        --#SEVERITY WARNING
        ::= { IntelligentServerServerTRAPObject 1444096 }

--  Microcontroller/Coprocessor Device Enabled 
    IntelligentServerMicrocontrollerDeviceEnabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Microcontroller/Coprocessor Device Enabled" 
        --#SEVERITY INFORMATION
        ::= 1444097
    IntelligentServerMicrocontrollerDeviceEnabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Microcontroller/Coprocessor Device Enabled" 
        --#SEVERITY INFORMATION
        ::= { IntelligentServerServerTRAPObject 1444097 }

-- ********************************************** 
-- *        Add-in Card         * 
-- ********************************************** 
-- Add-in Card State Deasserted 
    IntelligentServerAddInCardStateDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Add-in Card State Deasserted" 
        --#SEVERITY INFORMATION
        ::= 1508096
    IntelligentServerAddInCardStateDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Add-in Card State Deasserted" 
        --#SEVERITY INFORMATION
        ::= { IntelligentServerServerTRAPObject 1508096 }

-- Add-in Card State Asserted 
    IntelligentServerAddInCardStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Add-in Card State Asserted"
        --#SEVERITY INFORMATION
        ::= 1508097
    IntelligentServerAddInCardStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Add-in Card State Asserted"
        --#SEVERITY INFORMATION
        ::= { IntelligentServerServerTRAPObject 1508097 }

-- Add-in Card Predictive Failure Deasserted 
    IntelligentServerAddInCardPredictiveFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert } 
        STATUS current
        ENTERPRISE IntelligentServerServerTRAPObject
        DESCRIPTION
            "Add-in Card Predictive Failure Deasserted"
        --#SEVERITY INFORMATION
        ::= 1508352
    IntelligentServerAddInCardPredictiveFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert } 
        STATUS current
        DESCRIPTION
            "Add-in Card Predictive Failure Deasserted"
        --#SEVERITY INFORMATION
        ::= { IntelligentServerServerTRAPObject 1508352 }

-- Add-in Card Predictive Failure Asserted 
    IntelligentServerAddInCardPredictiveFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Add-in Card Predictive Failure Asserted"
        --#SEVERITY INFORMATION
        ::= 1508353
    IntelligentServerAddInCardPredictiveFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Add-in Card Predictive Failure Asserted"
        --#SEVERITY INFORMATION
        ::= { IntelligentServerServerTRAPObject 1508353 }

-- ********************************************** 
-- *        Chassis         * 
-- ********************************************** 
-- Chassis State Deasserted 
    IntelligentServerChassisStateDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis State Deasserted" 
        --#SEVERITY INFORMATION
        ::= 1573632
    IntelligentServerChassisStateDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis State Deasserted" 
        --#SEVERITY INFORMATION
        ::= { IntelligentServerServerTRAPObject 1573632 }

-- Chassis State Asserted 
    IntelligentServerChassisStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis State Asserted"
        --#SEVERITY INFORMATION
        ::= 1573633
    IntelligentServerChassisStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis State Asserted"
        --#SEVERITY INFORMATION
        ::= { IntelligentServerServerTRAPObject 1573633 }

-- Chassis Predictive Failure Deasserted 
    IntelligentServerChassisPredictiveFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis Predictive Failure Deasserted"
        --#SEVERITY INFORMATION
        ::= 1573888
    IntelligentServerChassisPredictiveFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis Predictive Failure Deasserted"
        --#SEVERITY INFORMATION
        ::= { IntelligentServerServerTRAPObject 1573888 }

-- Chassis Predictive Failure Asserted 
    IntelligentServerChassisPredictiveFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis Predictive Failure Asserted"
        --#SEVERITY CRITICAL
        ::= 1573889
    IntelligentServerChassisPredictiveFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis Predictive Failure Asserted"
        --#SEVERITY CRITICAL
        ::= { IntelligentServerServerTRAPObject 1573889 }
        
-- Chassis Transition to OK Assert
    IntelligentServerChassisTransitionToOK TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis Transition to OK Assert"
        --#SEVERITY WARNING
        ::= 1574656
    IntelligentServerChassisTransitionToOK-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis Transition to OK Assert"
        --#SEVERITY WARNING
        ::= { IntelligentServerServerTRAPObject 1574656 }
	
-- Chassis Transition to OK Deassert
    IntelligentServerChassisTransitiontoOK TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis Transition to OK Deassert"
        --#SEVERITY WARNING
        ::= 1574784
    IntelligentServerChassisTransitiontoOK-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis Transition to OK Deassert"
        --#SEVERITY WARNING
        ::= { IntelligentServerServerTRAPObject 1574784 }
	
-- Chassis Transition to Non-Critical from OK
    IntelligentServerChassisTransitionToNon-CriticalFromOK TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis Transition to Non-Critical from OK"
        --#SEVERITY WARNING
        ::= 1574657
    IntelligentServerChassisTransitionToNon-CriticalFromOK-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis Transition to Non-Critical from OK"
        --#SEVERITY WARNING
        ::= { IntelligentServerServerTRAPObject 1574657 }
	
-- Chassis Transition to OK from Non-Critical
    IntelligentServerChassisTransitiontoOKfromNon-Critical TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis Transition to OK from Non-Critical"
        --#SEVERITY WARNING
        ::= 1574785
    IntelligentServerChassisTransitiontoOKfromNon-Critical-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis Transition to OK from Non-Critical"
        --#SEVERITY WARNING
        ::= { IntelligentServerServerTRAPObject 1574785 }
-- Chassis Transition to Critical from less severe Asserted
    IntelligentServerChassisTransitionToCriticalFromlesssevereAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis Transition to Critical from less severe Asserted"
        --#SEVERITY WARNING
        ::= 1574658
    IntelligentServerChassisTransitionToCriticalFromlesssevereAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis Transition to Critical from less severe Asserted"
        --#SEVERITY WARNING
        ::= { IntelligentServerServerTRAPObject 1574658 }
	
-- Chassis Transition to Critical from less severe Deasserted
    IntelligentServerChassisTransitionToCriticalFromlesssevereDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chassis Transition to Critical from less severe Deasserted"
        --#SEVERITY WARNING
        ::= 1574786
    IntelligentServerChassisTransitionToCriticalFromlesssevereDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chassis Transition to Critical from less severe Deasserted"
        --#SEVERITY WARNING
        ::= { IntelligentServerServerTRAPObject 1574786 }
-- ********************************************** 
-- *        Chip Set            * 
-- ********************************************** 
-- Chip Set State Deasserted 
    IntelligentServerChipSetStateDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chip Set State Deasserted"
        --#SEVERITY INFORMATION
        ::= 1639168
    IntelligentServerChipSetStateDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chip Set State Deasserted"
        --#SEVERITY INFORMATION
        ::= { IntelligentServerServerTRAPObject 1639168 }

-- Chip Set State Asserted 
    IntelligentServerChipSetStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chip Set State Asserted"
        --#SEVERITY INFORMATION
        ::= 1639169
    IntelligentServerChipSetStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chip Set State Asserted"
        --#SEVERITY INFORMATION
        ::= { IntelligentServerServerTRAPObject 1639169 }

-- Chip Set Predictive Failure Deasserted 
    IntelligentServerChipSetPredictiveFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chip Set Predictive Failure Deasserted"
        --#SEVERITY INFORMATION
        ::= 1639424
    IntelligentServerChipSetPredictiveFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chip Set Predictive Failure Deasserted"
        --#SEVERITY INFORMATION
        ::= { IntelligentServerServerTRAPObject 1639424 }

-- Chip Set Predictive Failure Asserted 
    IntelligentServerChipSetPredictiveFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chip Set Predictive Failure Asserted"
        --#SEVERITY INFORMATION
        ::= 1639425
    IntelligentServerChipSetPredictiveFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chip Set Predictive Failure Asserted"
        --#SEVERITY INFORMATION
        ::= { IntelligentServerServerTRAPObject 1639425 }

-- Soft Power Control Failure 
    IntelligentServerSoftPowerControlFailure TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chip Set did not respond to BMC request to change system power state."
        --#SEVERITY WARNING
        ::= 1666816
    IntelligentServerSoftPowerControlFailure-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chip Set did not respond to BMC request to change system power state."
        --#SEVERITY WARNING
        ::= { IntelligentServerServerTRAPObject 1666816 }

-- Thermal Trip Occured 
    IntelligentServerThermalTrip TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Thermal Trip Occured"
        --#SEVERITY WARNING
        ::= 1666817
    IntelligentServerThermalTrip-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Thermal Trip Occured"
        --#SEVERITY WARNING
        ::= { IntelligentServerServerTRAPObject 1666817 }

-- Soft Power Control Failure Cleared 
    IntelligentServerSoftPowerControlFailureCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Chip Set started responding to BMC request to change system power state."
        --#SEVERITY INFORMATION
        ::= 1666944
    IntelligentServerSoftPowerControlFailureCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Chip Set started responding to BMC request to change system power state."
        --#SEVERITY INFORMATION
        ::= { IntelligentServerServerTRAPObject 1666944 }

-- Thermal Trip Cleared 
    IntelligentServerThermalTripCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Thermal Trip Cleared" 
        --#SEVERITY INFORMATION
        ::= 1666945
    IntelligentServerThermalTripCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Thermal Trip Cleared" 
        --#SEVERITY INFORMATION
        ::= { IntelligentServerServerTRAPObject 1666945 }

-- ********************************************** 
-- *        Other FRU           * 
-- ********************************************** 
-- FRU State Deasserted 
    IntelligentServerFRUStateDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU State Deasserted"
        --#SEVERITY INFORMATION
        ::= 1704704
    IntelligentServerFRUStateDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU State Deasserted"
        --#SEVERITY INFORMATION
        ::= { IntelligentServerServerTRAPObject 1704704 }

-- FRU State Asserted 
    IntelligentServerFRUStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU State Asserted"
        --#SEVERITY INFORMATION
        ::= 1704705
    IntelligentServerFRUStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU State Asserted"
        --#SEVERITY INFORMATION
        ::= { IntelligentServerServerTRAPObject 1704705 }

-- FRU Predictive Failure Deasserted 
    IntelligentServerFRUPredictiveFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU Predictive Failure Deasserted"
        --#SEVERITY INFORMATION
        ::= 1704960
    IntelligentServerFRUPredictiveFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU Predictive Failure Deasserted"
        --#SEVERITY INFORMATION
        ::= { IntelligentServerServerTRAPObject 1704960 }

-- FRU Predictive Failure Asserted 
    IntelligentServerFRUPredictiveFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU Predictive Failure Asserted"
        --#SEVERITY INFORMATION
        ::= 1704961
    IntelligentServerFRUPredictiveFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU Predictive Failure Asserted"
        --#SEVERITY INFORMATION
        ::= { IntelligentServerServerTRAPObject 1704961 }

-- ********************************************** 
-- *        Cable / Interconnect            * 
-- ********************************************** 
-- Cable / Interconnect State Deasserted 
    IntelligentServerCableStateDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cable / Interconnect State Deasserted"
        --#SEVERITY INFORMATION
        ::= 1770240
    IntelligentServerCableStateDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cable / Interconnect State Deasserted"
        --#SEVERITY INFORMATION
        ::= { IntelligentServerServerTRAPObject 1770240 }

-- Cable / Interconnect State Asserted 
    IntelligentServerCableStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cable / Interconnect State Asserted"
        --#SEVERITY WARNING
        ::= 1770241
    IntelligentServerCableStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cable / Interconnect State Asserted"
        --#SEVERITY WARNING
        ::= { IntelligentServerServerTRAPObject 1770241 }

-- Cable / Interconnect Predictive Failure Deasserted 
    IntelligentServerCablePredictiveFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cable / Interconnect Predictive Failure Deasserted"
        --#SEVERITY INFORMATION
        ::= 1770496
    IntelligentServerCablePredictiveFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cable / Interconnect Predictive Failure Deasserted"
        --#SEVERITY INFORMATION
        ::= { IntelligentServerServerTRAPObject 1770496 }

-- Cable / Interconnect Predictive Failure Asserted 
    IntelligentServerCablePredictiveFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cable / Interconnect Predictive Failure Asserted"
        --#SEVERITY WARNING
        ::= 1770497
    IntelligentServerCablePredictiveFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cable / Interconnect Predictive Failure Asserted"
        --#SEVERITY WARNING
        ::= { IntelligentServerServerTRAPObject 1770497 }

-- Cable/Interconnect is connected 
    IntelligentServerCableConnected TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cable/Interconnect is connected"
        --#SEVERITY INFORMATION
        ::= 1797888
    IntelligentServerCableConnected-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cable/Interconnect is connected"
        --#SEVERITY INFORMATION
        ::= { IntelligentServerServerTRAPObject 1797888 }

-- Configuration Error 
    IntelligentServerConfigurationError TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Configuration Error - Incorrect cable connected / Incorrect interconnection"
        --#SEVERITY WARNING
        ::= 1797889
    IntelligentServerConfigurationError-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Configuration Error - Incorrect cable connected / Incorrect interconnection"
        --#SEVERITY WARNING
        ::= { IntelligentServerServerTRAPObject 1797889 }

-- Cable/Interconnect is disconnected 
    IntelligentServerCableDisConnected TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Cable/Interconnect is disconnected"
        --#SEVERITY WARNING
        ::= 1798016
    IntelligentServerCableDisConnected-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Cable/Interconnect is disconnected"
        --#SEVERITY WARNING
        ::= { IntelligentServerServerTRAPObject 1798016 }

-- Configuration Error Cleared 
    IntelligentServerConfigurationErrorCleared TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Configuration Error Cleared"
        --#SEVERITY INFORMATION
        ::= 1798017
    IntelligentServerConfigurationErrorCleared-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Configuration Error Cleared"
        --#SEVERITY INFORMATION
        ::= { IntelligentServerServerTRAPObject 1798017 }

-- ********************************************** 
-- *        Terminator          * 
-- ********************************************** 
-- Terminator State Deasserted 
    IntelligentServerTerminatorStateDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Terminator State Deasserted"
        --#SEVERITY INFORMATION
        ::= 1835776
    IntelligentServerTerminatorStateDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Terminator State Deasserted"
        --#SEVERITY INFORMATION
        ::= { IntelligentServerServerTRAPObject 1835776 }

-- Terminator State Asserted 
    IntelligentServerTerminatorStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Terminator State Asserted"
        --#SEVERITY INFORMATION
        ::= 1835777
    IntelligentServerTerminatorStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Terminator State Asserted"
        --#SEVERITY INFORMATION
        ::= { IntelligentServerServerTRAPObject 1835777 }

-- Terminator Predictive Failure Deasserted 
    IntelligentServerTerminatorPredictiveFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Terminator Predictive Failure Deasserted"
        --#SEVERITY INFORMATION
        ::= 1836032
    IntelligentServerTerminatorPredictiveFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Terminator Predictive Failure Deasserted"
        --#SEVERITY INFORMATION
        ::= { IntelligentServerServerTRAPObject 1836032 }

-- Terminator Predictive Failure Asserted 
    IntelligentServerTerminatorPredictiveFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Terminator Predictive Failure Asserted"
        --#SEVERITY INFORMATION
        ::= 1836033
    IntelligentServerTerminatorPredictiveFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Terminator Predictive Failure Asserted"
        --#SEVERITY INFORMATION
        ::= { IntelligentServerServerTRAPObject 1836033 }

-- ********************************************** 
-- *        System Boot / Restart Initiated     * 
-- ********************************************** 

-- BIOS_Boot_Up State Asserted
    IntelligentServerBIOSBootUpStateAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "BIOS_Boot_Up State Asserted"
        --#SEVERITY INFORMATION
        ::= 1901313
    IntelligentServerBIOSBootUpStateAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "BIOS_Boot_Up State Asserted"
        --#SEVERITY INFORMATION
        ::= { IntelligentServerServerTRAPObject 1901313 }

-- System Boot / Restart Initiated by power up 
    IntelligentServerSystemBootByPowerUp TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "System Boot / Restart Initiated by power up"
        --#SEVERITY INFORMATION
        ::= 1928960
    IntelligentServerSystemBootByPowerUp-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "System Boot / Restart Initiated by power up"
        --#SEVERITY INFORMATION
        ::= { IntelligentServerServerTRAPObject 1928960 }

-- System Boot / Restart Initiated by Hard Reset 
    IntelligentServerSystemBootByHardReset TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart Initiated by Hard Reset"
        --#SEVERITY INFORMATION
        ::= 1928961
    IntelligentServerSystemBootByHardReset-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart Initiated by Hard Reset"
        --#SEVERITY INFORMATION
        ::= { IntelligentServerServerTRAPObject 1928961 }

-- System Boot / Restart Initiated by Warm Reset 
    IntelligentServerSystemBootByWarmReset TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart Initiated by Warm Reset"
        --#SEVERITY INFORMATION
        ::= 1928962
    IntelligentServerSystemBootByWarmReset-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart Initiated by Warm Reset"
        --#SEVERITY INFORMATION
        ::= { IntelligentServerServerTRAPObject 1928962 }

-- System Boot / Restart - User requested PXE boot 
    IntelligentServerUserRequestedPXEBoot TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart - User requested PXE boot"
        --#SEVERITY INFORMATION
        ::= 1928963
    IntelligentServerUserRequestedPXEBoot-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart - User requested PXE boot"
        --#SEVERITY INFORMATION
        ::= { IntelligentServerServerTRAPObject 1928963 }

-- System Boot / Restart - Automatic boot to diagnostic 
    IntelligentServerAutomaticDiagnosticBoot TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart - Automatic boot to diagnostic"
        --#SEVERITY INFORMATION
        ::= 1928964
    IntelligentServerAutomaticDiagnosticBoot-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart - Automatic boot to diagnostic"
        --#SEVERITY INFORMATION
        ::= { IntelligentServerServerTRAPObject 1928964 }

-- System Boot / Restart - OS / run-time software initiated hard reset 
    IntelligentServerOSInitiatedHardReset TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart - OS / run-time software initiated hard reset"
        --#SEVERITY INFORMATION
        ::= 1928965
    IntelligentServerOSInitiatedHardReset-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart - OS / run-time software initiated hard reset"
        --#SEVERITY INFORMATION
        ::= { IntelligentServerServerTRAPObject 1928965 }

-- System Boot / Restart - OS / run-time software initiated Warm reset 
    IntelligentServerOSInitiatedWarmReset TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart - OS / run-time software initiated Warm reset" 
        --#SEVERITY INFORMATION
        ::= 1928966
    IntelligentServerOSInitiatedWarmReset-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart - OS / run-time software initiated Warm reset" 
        --#SEVERITY INFORMATION
        ::= { IntelligentServerServerTRAPObject 1928966 }

-- System Boot / Restart - System Restart 
    IntelligentServerSystemRestart TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart - Restart cause per Get System Restart Cause command" 
        --#SEVERITY INFORMATION
        ::= 1928967
    IntelligentServerSystemRestart-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart - Restart cause per Get System Restart Cause command" 
        --#SEVERITY INFORMATION
        ::= { IntelligentServerServerTRAPObject 1928967 }

-- System Boot / Restart Initiated by power up Deasserted 
    IntelligentServerSystemBootByPowerUpDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "System Boot / Restart Initiated by power up Deasserted"
        --#SEVERITY INFORMATION
        ::= 1929088
    IntelligentServerSystemBootByPowerUpDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "System Boot / Restart Initiated by power up Deasserted"
        --#SEVERITY INFORMATION
        ::= { IntelligentServerServerTRAPObject 1929088 }

-- System Boot / Restart Initiated by Hard Reset Deasserted 
    IntelligentServerSystemBootByHardResetDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart Initiated by Hard Reset Deasserted" 
        --#SEVERITY INFORMATION
        ::= 1929089
    IntelligentServerSystemBootByHardResetDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart Initiated by Hard Reset Deasserted" 
        --#SEVERITY INFORMATION
        ::= { IntelligentServerServerTRAPObject 1929089 }

-- System Boot / Restart Initiated by Warm Reset Deasserted 
    IntelligentServerSystemBootByWarmResetDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart Initiated by Warm Reset Deasserted" 
        --#SEVERITY INFORMATION
        ::= 1929090
    IntelligentServerSystemBootByWarmResetDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart Initiated by Warm Reset Deasserted" 
        --#SEVERITY INFORMATION
        ::= { IntelligentServerServerTRAPObject 1929090 }

-- System Boot / Restart - User requested PXE boot Deasserted 
    IntelligentServerUserRequestedPXEBootDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart - User requested PXE boot Deasserted"
        --#SEVERITY INFORMATION
        ::= 1929091
    IntelligentServerUserRequestedPXEBootDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart - User requested PXE boot Deasserted"
        --#SEVERITY INFORMATION
        ::= { IntelligentServerServerTRAPObject 1929091 }

-- System Boot / Restart - Automatic boot to diagnostic Deasserted 
    IntelligentServerAutomaticDiagnosticBootDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart - Automatic boot to diagnostic Deasserted" 
        --#SEVERITY INFORMATION
        ::= 1929092
    IntelligentServerAutomaticDiagnosticBootDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart - Automatic boot to diagnostic Deasserted" 
        --#SEVERITY INFORMATION
        ::= { IntelligentServerServerTRAPObject 1929092 }

-- System Boot / Restart - OS / run-time software initiated hard reset Deasserted 
    IntelligentServerOSInitiatedHardResetDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart - OS / run-time software initiated hard reset Deasserted" 
        --#SEVERITY INFORMATION
        ::= 1929093
    IntelligentServerOSInitiatedHardResetDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart - OS / run-time software initiated hard reset Deasserted" 
        --#SEVERITY INFORMATION
        ::= { IntelligentServerServerTRAPObject 1929093 }

-- System Boot / Restart - OS / run-time software initiated Warm reset Deasserted 
    IntelligentServerOSInitiatedWarmResetDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart - OS / run-time software initiated Warm reset Deasserted" 
        --#SEVERITY INFORMATION
        ::= 1929094
    IntelligentServerOSInitiatedWarmResetDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart - OS / run-time software initiated Warm reset Deasserted" 
        --#SEVERITY INFORMATION
        ::= { IntelligentServerServerTRAPObject 1929094 }

-- System Boot / Restart - System Restart Deasserted 
    IntelligentServerSystemRestartDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System Boot / Restart - Restart cause per Get System Restart Cause command Deasserted" 
        --#SEVERITY INFORMATION
        ::= 1929095
    IntelligentServerSystemRestartDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System Boot / Restart - Restart cause per Get System Restart Cause command Deasserted" 
        --#SEVERITY INFORMATION
        ::= { IntelligentServerServerTRAPObject 1929095 }

-- ********************************************** 
-- *        Boot Error          * 
-- ********************************************** 

-- Boot Error - No bootable media 
    IntelligentServerNoBootableMedia TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Boot Error - No bootable media" 
        --#SEVERITY CRITICAL
        ::= 1994496
    IntelligentServerNoBootableMedia-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Boot Error - No bootable media" 
        --#SEVERITY CRITICAL
        ::= { IntelligentServerServerTRAPObject 1994496 }

-- Boot Error - Non-bootable diskette left in drive 
    IntelligentServerNonBootableDisketteInDrive TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Boot Error - Non-bootable diskette left in drive"
        --#SEVERITY CRITICAL
        ::= 1994497
    IntelligentServerNonBootableDisketteInDrive-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Boot Error - Non-bootable diskette left in drive"
        --#SEVERITY CRITICAL
        ::= { IntelligentServerServerTRAPObject 1994497 }

-- Boot Error - PXE Server not found 
    IntelligentServerPXEServerNotFound TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Boot Error - PXE Server not found"
        --#SEVERITY CRITICAL
        ::= 1994498 
    IntelligentServerPXEServerNotFound-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Boot Error - PXE Server not found"
        --#SEVERITY CRITICAL
        ::= { IntelligentServerServerTRAPObject 1994498  }

-- Boot Error - Invalid boot sector 
    IntelligentServerInvalidBootSector TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Boot Error - Invalid boot sector"
        --#SEVERITY CRITICAL
        ::= 1994499
    IntelligentServerInvalidBootSector-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Boot Error - Invalid boot sector"
        --#SEVERITY CRITICAL
        ::= { IntelligentServerServerTRAPObject 1994499 }

-- Boot Error - Timeout waiting for user selection of boot source 
    IntelligentServerTimeoutWaitingUserSelection TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Boot Error - Timeout waiting for user selection of boot source"
        --#SEVERITY INFORMATION
        ::= 1994500
    IntelligentServerTimeoutWaitingUserSelection-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Boot Error - Timeout waiting for user selection of boot source"
        --#SEVERITY INFORMATION
        ::= { IntelligentServerServerTRAPObject 1994500 }

-- Bootable media found 
    IntelligentServerFoundBootableMedia TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Found bootable media"
        --#SEVERITY INFORMATION
        ::= 1994624
    IntelligentServerFoundBootableMedia-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Found bootable media"
        --#SEVERITY INFORMATION
        ::= { IntelligentServerServerTRAPObject 1994624 }

-- Bootable diskette Found 
    IntelligentServerFoundBootableDisketteInDrive TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Bootable diskette Found"
        --#SEVERITY INFORMATION
        ::= 1994625
    IntelligentServerFoundBootableDisketteInDrive-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Bootable diskette Found"
        --#SEVERITY INFORMATION
        ::= { IntelligentServerServerTRAPObject 1994625 }

-- PXE Server  found 
    IntelligentServerPXEServerFound TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "PXE Server found"
        --#SEVERITY INFORMATION
        ::= 1994626 
    IntelligentServerPXEServerFound-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "PXE Server found"
        --#SEVERITY INFORMATION
        ::= { IntelligentServerServerTRAPObject 1994626  }

-- Found valid boot sector 
    IntelligentServerFoundValidBootSector TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Found valid boot sector"
        --#SEVERITY INFORMATION
        ::= 1994627
    IntelligentServerFoundValidBootSector-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Found valid boot sector"
        --#SEVERITY INFORMATION
        ::= { IntelligentServerServerTRAPObject 1994627 }

-- User selected boot source 
    IntelligentServerUserSelectedBootSource TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "User selected boot source"
        --#SEVERITY INFORMATION
        ::= 1994628
    IntelligentServerUserSelectedBootSource-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "User selected boot source"
        --#SEVERITY INFORMATION
        ::= { IntelligentServerServerTRAPObject 1994628 }

-- ********************************************** 
-- *        OS Boot         * 
-- ********************************************** 
-- A: boot completed 
    IntelligentServerBootCompletedDirectoryA TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "A: boot completed" 
        --#SEVERITY INFORMATION
        ::= 2060032
    IntelligentServerBootCompletedDirectoryA-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "A: boot completed" 
        --#SEVERITY INFORMATION
        ::= { IntelligentServerServerTRAPObject 2060032 }

 -- C: boot completed 
     IntelligentServerBootCompletedDirectoryC TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "C: boot completed"
        --#SEVERITY INFORMATION
        ::= 2060033
    IntelligentServerBootCompletedDirectoryC-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "C: boot completed"
        --#SEVERITY INFORMATION
        ::= { IntelligentServerServerTRAPObject 2060033 }

 -- PXE boot completed 
     IntelligentServerPXEBootCompleted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "PXE boot completed" 
        --#SEVERITY INFORMATION
        ::= 2060034
    IntelligentServerPXEBootCompleted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "PXE boot completed" 
        --#SEVERITY INFORMATION
        ::= { IntelligentServerServerTRAPObject 2060034 }

 -- Diagnostic boot completed 
     IntelligentServerDiagnosticBootCompleted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Diagnostic boot completed"
        --#SEVERITY INFORMATION
        ::= 2060035
    IntelligentServerDiagnosticBootCompleted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Diagnostic boot completed"
        --#SEVERITY INFORMATION
        ::= { IntelligentServerServerTRAPObject 2060035 }
 
  -- CDROM boot completed 
      IntelligentServerCDROMBootCompleted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CDROM boot completed"
        --#SEVERITY INFORMATION
        ::= 2060036
    IntelligentServerCDROMBootCompleted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CDROM boot completed"
        --#SEVERITY INFORMATION
        ::= { IntelligentServerServerTRAPObject 2060036 }

 -- ROM boot completed 
     IntelligentServerROMBootCompleted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "ROM boot completed"
        --#SEVERITY INFORMATION
        ::= 2060037
    IntelligentServerROMBootCompleted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "ROM boot completed"
        --#SEVERITY INFORMATION
        ::= { IntelligentServerServerTRAPObject 2060037 }

 -- Boot completed - boot device not specified 
     IntelligentServerBootCompletedUnknownSource TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Boot completed - boot device not specified" 
        --#SEVERITY INFORMATION
        ::= 2060038
    IntelligentServerBootCompletedUnknownSource-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Boot completed - boot device not specified" 
        --#SEVERITY INFORMATION
        ::= { IntelligentServerServerTRAPObject 2060038 }
 
 -- A: boot incomplete 
     IntelligentServerBootIncompleteDirectoryA TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "A: boot incomplete" 
        --#SEVERITY WARNING
        ::= 2060160
    IntelligentServerBootIncompleteDirectoryA-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "A: boot incomplete" 
        --#SEVERITY WARNING
        ::= { IntelligentServerServerTRAPObject 2060160 }

 -- C: boot incomplete 
     IntelligentServerBootIncompleteDirectoryC TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "C: boot incomplete" 
        --#SEVERITY WARNING
        ::= 2060161
    IntelligentServerBootIncompleteDirectoryC-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "C: boot incomplete" 
        --#SEVERITY WARNING
        ::= { IntelligentServerServerTRAPObject 2060161 }

 -- PXE boot Incomplete 
     IntelligentServerPXEBootIncomplete TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "PXE boot Incomplete"
        --#SEVERITY WARNING
        ::= 2060162
    IntelligentServerPXEBootIncomplete-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "PXE boot Incomplete"
        --#SEVERITY WARNING
        ::= { IntelligentServerServerTRAPObject 2060162 }

 -- Diagnostic boot Incomplete 
     IntelligentServerDiagnosticBootIncomplete TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Diagnostic boot Incomplete"
        --#SEVERITY WARNING
        ::= 2060163
    IntelligentServerDiagnosticBootIncomplete-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Diagnostic boot Incomplete"
        --#SEVERITY WARNING
        ::= { IntelligentServerServerTRAPObject 2060163 }
 
  -- CDROM boot Incomplete 
      IntelligentServerCDROMBootIncomplete TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CDROM boot Incomplete"
        --#SEVERITY WARNING
        ::= 2060164
    IntelligentServerCDROMBootIncomplete-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CDROM boot Incomplete"
        --#SEVERITY WARNING
        ::= { IntelligentServerServerTRAPObject 2060164 }

 -- ROM boot Incomplete 
     IntelligentServerROMBootIncomplete TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "ROM boot Incomplete" 
        --#SEVERITY WARNING
        ::= 2060165
    IntelligentServerROMBootIncomplete-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "ROM boot Incomplete" 
        --#SEVERITY WARNING
        ::= { IntelligentServerServerTRAPObject 2060165 }

 -- Boot Incomplete - boot device not specified
    IntelligentServerBootIncompleteUnknownSource TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Boot Incomplete - boot device not specified" 
        --#SEVERITY WARNING
        ::= 2060166 
    IntelligentServerBootIncompleteUnknownSource-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Boot Incomplete - boot device not specified" 
        --#SEVERITY WARNING
        ::= { IntelligentServerServerTRAPObject 2060166 }

-- ********************************************** 
-- *        OS Stop / Shutdown          * 
-- ********************************************** 

 -- OS Stop / Shutdown - Stop during OS load / initialization 
     IntelligentServerOSStopDuringLoad TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Stop / Shutdown - Stop during OS load / initialization. Unexpected error uring system startup. Stopped waiting for input or power cycle/reset" 
        --#SEVERITY CRITICAL
        ::= 2125568
    IntelligentServerOSStopDuringLoad-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Stop / Shutdown - Stop during OS load / initialization. Unexpected error uring system startup. Stopped waiting for input or power cycle/reset" 
        --#SEVERITY CRITICAL
        ::= { IntelligentServerServerTRAPObject 2125568 }
 
  -- OS Stop / Shutdown - Run-time Critical Stop 
    IntelligentServerOSRuntimeCriticalStop TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Stop / Shutdown - Run-time Critical Stop" 
        --#SEVERITY CRITICAL
        ::= 2125569
    IntelligentServerOSRuntimeCriticalStop-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Stop / Shutdown - Run-time Critical Stop" 
        --#SEVERITY CRITICAL
        ::= { IntelligentServerServerTRAPObject 2125569 }

-- OS Stop / Shutdown - Graceful Stop 
    IntelligentServerOSGracefulStop TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Stop / Shutdown - Graceful Stop (system powered up, but normal OS operation has shut down and system is awaiting reset pushbutton, powercycle or other external input)"
        --#SEVERITY INFORMATION
        ::= 2125570
    IntelligentServerOSGracefulStop-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Stop / Shutdown - Graceful Stop (system powered up, but normal OS operation has shut down and system is awaiting reset pushbutton, powercycle or other external input)"
        --#SEVERITY INFORMATION
        ::= { IntelligentServerServerTRAPObject 2125570 }
  
-- OS Stop / Shutdown - Graceful Shutdown 
    IntelligentServerOSGracefulShutdown TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Stop / Shutdown - Graceful Shutdown (system graceful power down by OS)"
        --#SEVERITY INFORMATION
        ::= 2125571
    IntelligentServerOSGracefulShutdown-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Stop / Shutdown - Graceful Shutdown (system graceful power down by OS)"
        --#SEVERITY INFORMATION
        ::= { IntelligentServerServerTRAPObject 2125571 }

-- OS Stop / Shutdown - Soft Shutdown initiated by PEF 
    IntelligentServerOSSoftShutdownInitiatedByPEF TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Stop / Shutdown - Soft Shutdown initiated by PEF"
        --#SEVERITY INFORMATION
        ::= 2125572
    IntelligentServerOSSoftShutdownInitiatedByPEF-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Stop / Shutdown - Soft Shutdown initiated by PEF"
        --#SEVERITY INFORMATION
        ::= { IntelligentServerServerTRAPObject 2125572 }

-- OS Stop / Shutdown - Agent Not Responding 
    IntelligentServerOSAgentNotResponding TRAP-TYPE
    OBJECTS { altHostLocation, altTrapTime, altSysManufacture, altSysModel, altSensorName, altSensorType, altSensorReading, altSensorThreshold, altHostContact, altBMCHostName, altSysName, altSpTxtId, altPriority, altEventAssertOrDeassert }
    STATUS current
    ENTERPRISE IntelligentServerServerTRAPObject
    DESCRIPTION
        "OS Stop / Shutdown - Agent Not Responding"
        --#SEVERITY CRITICAL
    ::= 2125573
    IntelligentServerOSAgentNotResponding-V2cV3 NOTIFICATION-TYPE
    OBJECTS { altHostLocation, altTrapTime, altSysManufacture, altSysModel, altSensorName, altSensorType, altSensorReading, altSensorThreshold, altHostContact, altBMCHostName, altSysName, altSpTxtId, altPriority, altEventAssertOrDeassert }
    STATUS current
    DESCRIPTION
        "OS Stop / Shutdown - Agent Not Responding"
        --#SEVERITY CRITICAL
    ::= { IntelligentServerServerTRAPObject 2125573 }
 
  -- OS Stop / Shutdown - Stop during OS load / initialization Deasserted 
    IntelligentServerOSStopDuringLoadDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Stop / Shutdown - power cycle/reset Done"
        --#SEVERITY INFORMATION
        ::= 2125696
    IntelligentServerOSStopDuringLoadDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Stop / Shutdown - power cycle/reset Done"
        --#SEVERITY INFORMATION
        ::= { IntelligentServerServerTRAPObject 2125696 }
 
  -- OS Stop / Shutdown - Run-time Information Stop Deasserted 
    IntelligentServerOSRuntimeInformationStopDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "OS Stop / Shutdown -Power Cycle/Reset Done"
        --#SEVERITY INFORMATION
        ::= 2125697
    IntelligentServerOSRuntimeInformationStopDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "OS Stop / Shutdown -Power Cycle/Reset Done"
        --#SEVERITY INFORMATION
        ::= { IntelligentServerServerTRAPObject 2125697 }

-- OS Stop / Shutdown - Graceful Stop Deasserted 
    IntelligentServerOSGracefulStopDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Stop / Shutdown - System powered up by reset pushbutton, powercycle or other external input" 
        --#SEVERITY INFORMATION
        ::= 2125698
    IntelligentServerOSGracefulStopDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Stop / Shutdown - System powered up by reset pushbutton, powercycle or other external input" 
        --#SEVERITY INFORMATION
        ::= { IntelligentServerServerTRAPObject 2125698 }
  
-- OS Stop / Shutdown - Graceful Shutdown Deasserted 
    IntelligentServerOSGracefulShutdownDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Stop / Shutdown - System powered by reset pushbutton, powercycle or other external input" 
        --#SEVERITY INFORMATION
        ::= 2125699
    IntelligentServerOSGracefulShutdownDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Stop / Shutdown - System powered by reset pushbutton, powercycle or other external input" 
        --#SEVERITY INFORMATION
        ::= { IntelligentServerServerTRAPObject 2125699 }

-- OS Stop / Shutdown - Soft Shutdown Deasserted 
    IntelligentServerOSSoftShutdownDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Stop / Shutdown - System powered by reset pushbutton, powercycle or other external input"
        --#SEVERITY INFORMATION
        ::= 2125700
    IntelligentServerOSSoftShutdownDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Stop / Shutdown - System powered by reset pushbutton, powercycle or other external input"
        --#SEVERITY INFORMATION
        ::= { IntelligentServerServerTRAPObject 2125700 }

-- OS Stop / Shutdown - Agent Started Responding 
    IntelligentServerOSAgentNotRespondingDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "OS Stop / Shutdown - Agent Started Responding"
        --#SEVERITY INFORMATION
        ::= 2125701
    IntelligentServerOSAgentNotRespondingDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "OS Stop / Shutdown - Agent Started Responding"
        --#SEVERITY INFORMATION
        ::= { IntelligentServerServerTRAPObject 2125701 }

-- ********************************************** 
-- *        Slot / Connector            * 
-- ********************************************** 

-- Slot / Connector - Fault Status asserted 
    IntelligentServerSlotFaultStatusAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Slot / Connector - Fault Status asserted" 
        --#SEVERITY WARNING
        ::= 2191104
    IntelligentServerSlotFaultStatusAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Slot / Connector - Fault Status asserted" 
        --#SEVERITY WARNING
        ::= { IntelligentServerServerTRAPObject 2191104 }

-- Slot / Connector - Identify Status asserted 
    IntelligentServerSlotIdentifyStatusAsserted TRAP-TYPE
        OBJECTS { altHostLocation, altTrapTime, altSysManufacture, altSysModel, altSensorName, altSensorType, altSensorReading, altSensorThreshold, altHostContact, altBMCHostName, altSysName, altSpTxtId, altPriority, altEventAssertOrDeassert } 
        STATUS current
        ENTERPRISE IntelligentServerServerTRAPObject
        DESCRIPTION
            "Slot / Connector - Identify Status asserted"
        --#SEVERITY INFORMATION
        ::= 2191105
    IntelligentServerSlotIdentifyStatusAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert } 
        STATUS current
        DESCRIPTION
            "Slot / Connector - Identify Status asserted"
        --#SEVERITY INFORMATION
        ::= { IntelligentServerServerTRAPObject 2191105 }

-- Slot / Connector - Device installed/attached 
    IntelligentServerSlotDeviceInstalledOrAttached TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Device installed/attached"
        --#SEVERITY INFORMATION
        ::= 2191106
    IntelligentServerSlotDeviceInstalledOrAttached-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Device installed/attached"
        --#SEVERITY INFORMATION
        ::= { IntelligentServerServerTRAPObject 2191106 }

-- Slot / Connector - Ready for Device Installation 
    IntelligentServerSlotReadyForDeviceInstallation TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Ready for Device Installation. Typically, this means that the slot power is off"
        --#SEVERITY INFORMATION
        ::= 2191107
    IntelligentServerSlotReadyForDeviceInstallation-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Ready for Device Installation. Typically, this means that the slot power is off"
        --#SEVERITY INFORMATION
        ::= { IntelligentServerServerTRAPObject 2191107 }

-- Slot / Connector - Ready for Device Removal 
    IntelligentServerSlotReadyForDeviceRemoval TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Slot / Connector - Ready for Device Removal. Typically, this means that the slot power is off"
        --#SEVERITY INFORMATION
        ::= 2191108
    IntelligentServerSlotReadyForDeviceRemoval-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Slot / Connector - Ready for Device Removal. Typically, this means that the slot power is off"
        --#SEVERITY INFORMATION
        ::= { IntelligentServerServerTRAPObject 2191108 }

-- Slot / Connector - Slot Power is Off 
    IntelligentServerSlotPowerIsOff TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Slot Power is Off"
        --#SEVERITY INFORMATION
        ::= 2191109
    IntelligentServerSlotPowerIsOff-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Slot Power is Off"
        --#SEVERITY INFORMATION
        ::= { IntelligentServerServerTRAPObject 2191109 }

-- Slot / Connector - Device Removal Request 
    IntelligentServerSlotDeviceRemovalRequest TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Slot / Connector - Device Removal Request"
        --#SEVERITY INFORMATION
        ::= 2191110
    IntelligentServerSlotDeviceRemovalRequest-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Slot / Connector - Device Removal Request"
        --#SEVERITY INFORMATION
        ::= { IntelligentServerServerTRAPObject 2191110 }

-- Slot / Connector - Interlock asserted 
    IntelligentServerSlotInterlockAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Interlock asserted" 
        --#SEVERITY INFORMATION
        ::= { IntelligentServerServerTRAPObject 2191111 }

-- Slot / Connector - Disabled 
    IntelligentServerSlotInterlockAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Interlock asserted" 
        --#SEVERITY INFORMATION
        ::= 2191111
        
    IntelligentServerSlotDisabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Disabled"
        --#SEVERITY INFORMATION
        ::= 2191112
    IntelligentServerSlotDisabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Disabled"
        --#SEVERITY INFORMATION
        ::= { IntelligentServerServerTRAPObject 2191112 }

-- Slot / Connector - holds spare device 
    IntelligentServerSlotHoldsSpareDevice TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - holds spare device"
        --#SEVERITY INFORMATION
        ::= 2191113
    IntelligentServerSlotHoldsSpareDevice-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - holds spare device"
        --#SEVERITY INFORMATION
        ::= { IntelligentServerServerTRAPObject 2191113 }

-- Slot / Connector - Fault Status Deasserted 
    IntelligentServerSlotFaultStatusDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Fault Status Deasserted"
        --#SEVERITY INFORMATION
        ::= 2191232
    IntelligentServerSlotFaultStatusDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Fault Status Deasserted"
        --#SEVERITY INFORMATION
        ::= { IntelligentServerServerTRAPObject 2191232 }

-- Slot / Connector - Identify Status Deasserted 
    IntelligentServerSlotIdentifyStatusDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Identify Status Deasserted" 
        --#SEVERITY INFORMATION
        ::= 2191233
    IntelligentServerSlotIdentifyStatusDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Identify Status Deasserted" 
        --#SEVERITY INFORMATION
        ::= { IntelligentServerServerTRAPObject 2191233 }

-- Slot / Connector - Device Removed 
    IntelligentServerSlotDeviceRemoved TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Device Uninstalled/Removed"
        --#SEVERITY INFORMATION
        ::= 2191234
    IntelligentServerSlotDeviceRemoved-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Device Uninstalled/Removed"
        --#SEVERITY INFORMATION
        ::= { IntelligentServerServerTRAPObject 2191234 }

-- Slot / Connector - Not Ready for Device Installation 
    IntelligentServerSlotNotReadyForDeviceInstallation TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Not Ready for Device Installation. Typically, this means that the slot power is on" 
        --#SEVERITY INFORMATION
        ::= 2191235
    IntelligentServerSlotNotReadyForDeviceInstallation-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Not Ready for Device Installation. Typically, this means that the slot power is on" 
        --#SEVERITY INFORMATION
        ::= { IntelligentServerServerTRAPObject 2191235 }

-- Slot / Connector - Not Ready for Device Removal 
    IntelligentServerSlotNotReadyForDeviceRemoval TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Not Ready for Device Removal. Typically, this means that the slot power is on" 
        --#SEVERITY INFORMATION
        ::= 2191236
    IntelligentServerSlotNotReadyForDeviceRemoval-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Not Ready for Device Removal. Typically, this means that the slot power is on" 
        --#SEVERITY INFORMATION
        ::= { IntelligentServerServerTRAPObject 2191236 }

-- Slot / Connector - Slot Power is On 
    IntelligentServerSlotPowerIsOn TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Slot Power is On" 
        --#SEVERITY INFORMATION
        ::= 2191237
    IntelligentServerSlotPowerIsOn-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Slot Power is On" 
        --#SEVERITY INFORMATION
        ::= { IntelligentServerServerTRAPObject 2191237 }

-- Slot / Connector - Device Removal Request Processed 
    IntelligentServerSlotDeviceRemovalRequestProcessed TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Device Removal Request Processed" 
        --#SEVERITY INFORMATION
        ::= 2191238
    IntelligentServerSlotDeviceRemovalRequestProcessed-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Device Removal Request Processed" 
        --#SEVERITY INFORMATION
        ::= { IntelligentServerServerTRAPObject 2191238 }

-- Slot / Connector - Interlock Deasserted 
    IntelligentServerSlotInterlockDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Interlock Deasserted" 
        --#SEVERITY INFORMATION
        ::= 2191239
    IntelligentServerSlotInterlockDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Interlock Deasserted" 
        --#SEVERITY INFORMATION
        ::= { IntelligentServerServerTRAPObject 2191239 }

-- Slot / Connector - Enabled 
    IntelligentServerSlotEnabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - Enabled" 
        --#SEVERITY INFORMATION
        ::= 2191240
    IntelligentServerSlotEnabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - Enabled" 
        --#SEVERITY INFORMATION
        ::= { IntelligentServerServerTRAPObject 2191240 }

-- Slot / Connector - frees spare device 
    IntelligentServerSlotFreesSpareDevice TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Slot / Connector - frees spare device"
        --#SEVERITY INFORMATION
        ::= 2191241
    IntelligentServerSlotFreesSpareDevice-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Slot / Connector - frees spare device"
        --#SEVERITY INFORMATION
        ::= { IntelligentServerServerTRAPObject 2191241 }

-- ********************************************** 
-- *        System ACPI Power State         * 
-- ********************************************** 
-- System ACPI Power State - S0 / G0 working 
    IntelligentServerACPIStateS0Working TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - S0 / G0 - Working"
        --#SEVERITY INFORMATION
        ::= 2256640
    IntelligentServerACPIStateS0Working-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - S0 / G0 - Working"
        --#SEVERITY INFORMATION
        ::= { IntelligentServerServerTRAPObject 2256640 }

-- System ACPI Power State - S1 
    IntelligentServerACPIStateS1 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - S1 - sleeping with system h/w & processor context maintained" 
        --#SEVERITY INFORMATION
        ::= 2256641
    IntelligentServerACPIStateS1-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - S1 - sleeping with system h/w & processor context maintained" 
        --#SEVERITY INFORMATION
        ::= { IntelligentServerServerTRAPObject 2256641 }

-- System ACPI Power State - S2  
    IntelligentServerACPIStateS2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - S2 sleeping, processor context lost"
        --#SEVERITY INFORMATION
        ::= 2256642
    IntelligentServerACPIStateS2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - S2 sleeping, processor context lost"
        --#SEVERITY INFORMATION
        ::= { IntelligentServerServerTRAPObject 2256642 }

-- System ACPI Power State - S3 
    IntelligentServerACPIStateS3 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - S3"
        --#SEVERITY INFORMATION
        ::= 2256643
    IntelligentServerACPIStateS3-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - S3"
        --#SEVERITY INFORMATION
        ::= { IntelligentServerServerTRAPObject 2256643 }

-- System ACPI Power State - S4 
    IntelligentServerACPIStateS4 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - S4 - non-volatile sleep / suspend-to disk"
        --#SEVERITY INFORMATION
        ::= 2256644
    IntelligentServerACPIStateS4-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - S4 - non-volatile sleep / suspend-to disk"
        --#SEVERITY INFORMATION
        ::= { IntelligentServerServerTRAPObject 2256644 }

-- System ACPI Power State - S5 / G2 
    IntelligentServerACPIStateS5 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - S5 / G2 - soft-off"
        --#SEVERITY INFORMATION
        ::= 2256645
    IntelligentServerACPIStateS5-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - S5 / G2 - soft-off"
        --#SEVERITY INFORMATION
        ::= { IntelligentServerServerTRAPObject 2256645 }

-- System ACPI Power State - S4 / S5 soft-off 
    IntelligentServerACPIStateS4OrS5SoftOff TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - S4 / S5 soft-off, particular S4 / S5 state cannot be determi"
        --#SEVERITY INFORMATION
        ::= 2256646
    IntelligentServerACPIStateS4OrS5SoftOff-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - S4 / S5 soft-off, particular S4 / S5 state cannot be determi"
        --#SEVERITY INFORMATION
        ::= { IntelligentServerServerTRAPObject 2256646 }

-- System ACPI Power State - G3 
    IntelligentServerACPIStateG3 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - G3 - Mechanical Off"
        --#SEVERITY INFORMATION
        ::= 2256647
    IntelligentServerACPIStateG3-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - G3 - Mechanical Off"
        --#SEVERITY INFORMATION
        ::= { IntelligentServerServerTRAPObject 2256647 }

-- System ACPI Power State - Sleeping in an S1, S2, or S3 states 
    IntelligentServerACPISleepingInUnknownState TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - Sleeping in an S1, S2, or S3 states" 
        --#SEVERITY INFORMATION
        ::= 2256648
    IntelligentServerACPISleepingInUnknownState-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - Sleeping in an S1, S2, or S3 states" 
        --#SEVERITY INFORMATION
        ::= { IntelligentServerServerTRAPObject 2256648 }

-- System ACPI Power State - G1  
    IntelligentServerACPIStateG1 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - G1 - sleeping (S1-S4 state cannot be determined)" 
        --#SEVERITY INFORMATION
        ::= 2256649
    IntelligentServerACPIStateG1-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - G1 - sleeping (S1-S4 state cannot be determined)" 
        --#SEVERITY INFORMATION
        ::= { IntelligentServerServerTRAPObject 2256649 }

-- System ACPI Power State - S5 entered by override 
    IntelligentServerACPIStateS5ByOverride TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - S5 entered by override" 
        --#SEVERITY INFORMATION
        ::= 2256650
    IntelligentServerACPIStateS5ByOverride-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - S5 entered by override" 
        --#SEVERITY INFORMATION
        ::= { IntelligentServerServerTRAPObject 2256650 }

-- System ACPI Power State - Legacy ON state 
    IntelligentServerACPILegacyONState TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - Legacy ON state" 
        --#SEVERITY INFORMATION
        ::= 2256651
    IntelligentServerACPILegacyONState-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - Legacy ON state" 
        --#SEVERITY INFORMATION
        ::= { IntelligentServerServerTRAPObject 2256651 }

-- System ACPI Power State - Legacy OFF state 
    IntelligentServerACPILegacyOFFState TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "System ACPI Power State - Legacy OFF state"
        --#SEVERITY INFORMATION
        ::= 2256652
    IntelligentServerACPILegacyOFFState-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "System ACPI Power State - Legacy OFF state"
        --#SEVERITY INFORMATION
        ::= { IntelligentServerServerTRAPObject 2256652 }

-- System ACPI Power State - Unknown 
    IntelligentServerACPIStateUnknown TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
         "System ACPI Power State - Unknown"
        --#SEVERITY INFORMATION
        ::= 2256654
    IntelligentServerACPIStateUnknown-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
         "System ACPI Power State - Unknown"
        --#SEVERITY INFORMATION
        ::= { IntelligentServerServerTRAPObject 2256654 }

-- ********************************************** 
-- *        Watchdog 2          * 
-- ********************************************** 
-- Watchdog timer expired 
    IntelligentServerWatchdogTimerExpired TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Watchdog timer expired, status only (no action, no interrupt)"
        --#SEVERITY WARNING
        ::=  2322176
    IntelligentServerWatchdogTimerExpired-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Watchdog timer expired, status only (no action, no interrupt)"
        --#SEVERITY WARNING
        ::= { IntelligentServerServerTRAPObject  2322176 }

-- Watchdog reset event 
    IntelligentServerWatchdogResetV TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Watchdog Reset" 
        --#SEVERITY CRITICAL
        ::=  2322177
    IntelligentServerWatchdogReset-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Watchdog Reset" 
        --#SEVERITY CRITICAL
        ::= { IntelligentServerServerTRAPObject  2322177 }

-- Watchdog power down event 
    IntelligentServerWatchdogPowerDown TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Watchdog Power Down" 
        --#SEVERITY CRITICAL
        ::=  2322178
    IntelligentServerWatchdogPowerDown-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Watchdog Power Down" 
        --#SEVERITY CRITICAL
        ::= { IntelligentServerServerTRAPObject  2322178 }

-- Watchdog power cycle event 
    IntelligentServerWatchdogPowerCycle TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Watchdog Power Cycle" 
        --#SEVERITY WARNING
        ::= 2322179
    IntelligentServerWatchdogPowerCycle-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Watchdog Power Cycle" 
        --#SEVERITY WARNING
        ::= { IntelligentServerServerTRAPObject 2322179 }

-- Watchdog Timer interrupt 
    IntelligentServerWatchdogTimerInterrupt TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Watchdog Timer interrupt"
        --#SEVERITY INFORMATION
        ::= 2322184
    IntelligentServerWatchdogTimerInterrupt-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Watchdog Timer interrupt"
        --#SEVERITY INFORMATION
        ::= { IntelligentServerServerTRAPObject 2322184 }

-- Watchdog timer Reset 
    IntelligentServerWatchdogTimerExpiredDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Watchdog timer Reset" 
        --#SEVERITY WARNING
        ::=  2322304
    IntelligentServerWatchdogTimerExpiredDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Watchdog timer Reset" 
        --#SEVERITY WARNING
        ::= { IntelligentServerServerTRAPObject  2322304 }

-- Watchdog reset event Deasserted 
    IntelligentServerWatchdogResetDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Watchdog Reset Deasserted" 
        --#SEVERITY CRITICAL
        ::=  2322305
    IntelligentServerWatchdogResetDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Watchdog Reset Deasserted" 
        --#SEVERITY CRITICAL
        ::= { IntelligentServerServerTRAPObject  2322305 }

-- Watchdog power down event Deasserted 
    IntelligentServerWatchdogPowerDownDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Watchdog Power Down Deasserted" 
        --#SEVERITY CRITICAL
        ::=  2322306
    IntelligentServerWatchdogPowerDownDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Watchdog Power Down Deasserted" 
        --#SEVERITY CRITICAL
        ::= { IntelligentServerServerTRAPObject  2322306 }

-- Watchdog power cycle event Deasserted 
    IntelligentServerWatchdogPowerCycleDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Watchdog Power Cycle Deasserted"
        --#SEVERITY WARNING
        ::= 2322307
    IntelligentServerWatchdogPowerCycleDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Watchdog Power Cycle Deasserted"
        --#SEVERITY WARNING
        ::= { IntelligentServerServerTRAPObject 2322307 }

-- Watchdog Timer interrupt Deasserted 
    IntelligentServerWatchdogTimerInterruptDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Watchdog Timer interrupt Deasserted" 
        --#SEVERITY INFORMATION
        ::= 2322312
    IntelligentServerWatchdogTimerInterruptDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Watchdog Timer interrupt Deasserted" 
        --#SEVERITY INFORMATION
        ::= { IntelligentServerServerTRAPObject 2322312 }

-- ********************************************** 
-- *        Platform Alert          * 
-- ********************************************** 
-- Platform Alert - platform generated page 
    IntelligentServerPlatformGeneratedPage TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Platform Alert - platform generated page"
        --#SEVERITY INFORMATION
        ::= 2387712
    IntelligentServerPlatformGeneratedPage-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Platform Alert - platform generated page"
        --#SEVERITY INFORMATION
        ::= { IntelligentServerServerTRAPObject 2387712 }

-- Platform Alert platform generated LAN alert 
    IntelligentServerPlatformGeneratedLANAlert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Platform Alert - platform generated LAN alert"
        --#SEVERITY INFORMATION
        ::= 2387713
    IntelligentServerPlatformGeneratedLANAlert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Platform Alert - platform generated LAN alert"
        --#SEVERITY INFORMATION
        ::= { IntelligentServerServerTRAPObject 2387713 }

-- Platform Alert Platform Event Trap generated 
    IntelligentServerPlatformPETFormatTrap TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Platform Alert - Platform Event Trap generated"
        --#SEVERITY INFORMATION
        ::= 2387714
    IntelligentServerPlatformPETFormatTrap-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Platform Alert - Platform Event Trap generated"
        --#SEVERITY INFORMATION
        ::= { IntelligentServerServerTRAPObject 2387714 }

-- Platform Alert platform generated SNMP IntelligentServer, OEM format 
    IntelligentServerPlatformOEMFormatTrap TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Platform Alert - platform generated SNMP IntelligentServer, OEM format"
        --#SEVERITY INFORMATION
        ::= 2387715
    IntelligentServerPlatformOEMFormatTrap-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Platform Alert - platform generated SNMP IntelligentServer, OEM format"
        --#SEVERITY INFORMATION
        ::= { IntelligentServerServerTRAPObject 2387715 }

-- ********************************************** 
-- *        Entity Presence         * 
-- ********************************************** 
-- A device is present or has been removed 
    IntelligentServerEntityPresenceDeviceRemovedOrAbsent TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "A device is absent or has been removed."
        --#SEVERITY CRITICAL
        ::= 2426880
-- A device is present or has been removed 
    IntelligentServerEntityPresenceDeviceRemovedOrAbsent-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "A device is absent or has been removed."
        --#SEVERITY CRITICAL
        ::= { IntelligentServerServerTRAPObject 2426880 }

-- A device is present or has been inserted 
    IntelligentServerEntityPresenceDeviceInsertedOrPresent TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "A device is present or has been inserted."
        --#SEVERITY INFORMATION
        ::= 2426881
    IntelligentServerEntityPresenceDeviceInsertedOrPresent-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "A device is present or has been inserted."
        --#SEVERITY INFORMATION
        ::= { IntelligentServerServerTRAPObject 2426881 }

-- Entity Present 
    IntelligentServerEntityPresent TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "The Entity identified by the Entity ID for the sensor is present."
        --#SEVERITY INFORMATION
        ::= 2453248
    IntelligentServerEntityPresent-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "The Entity identified by the Entity ID for the sensor is present."
        --#SEVERITY INFORMATION
        ::= { IntelligentServerServerTRAPObject 2453248 }

-- Entity Absent. 
    IntelligentServerEntityAbsent TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "The Entity identified by the Entity ID for the sensor is Absent." 
        --#SEVERITY INFORMATION
        ::= 2453249
    IntelligentServerEntityAbsent-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "The Entity identified by the Entity ID for the sensor is Absent." 
        --#SEVERITY INFORMATION
        ::= { IntelligentServerServerTRAPObject 2453249 }

 -- Entity Disabled.. 
     IntelligentServerEntityDisabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "The Entity identified by the Entity ID for the sensor is Disabled."
        --#SEVERITY INFORMATION
        ::= 2453250
    IntelligentServerEntityDisabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "The Entity identified by the Entity ID for the sensor is Disabled."
        --#SEVERITY INFORMATION
        ::= { IntelligentServerServerTRAPObject 2453250 }

-- ********************************************** 
-- *               LAN                  * 
-- ********************************************** 
-- LAN Heartbeat Lost
    IntelligentServerLANHeartbeatLost TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "LAN Heartbeat Lost"
        --#SEVERITY INFORMATION
        ::= 2584320
    IntelligentServerLANHeartbeatLost-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "LAN Heartbeat Lost"
        --#SEVERITY INFORMATION
        ::= { IntelligentServerServerTRAPObject 2584320 }

-- LAN Heartbeat
    IntelligentServerIntelligentServerLANHeartbeat TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "LAN Heartbeat"
        --#SEVERITY INFORMATION
        ::= 2584321
    IntelligentServerIntelligentServerLANHeartbeat-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "LAN Heartbeat"
        --#SEVERITY INFORMATION
        ::= { IntelligentServerServerTRAPObject 2584321 }

 
-- ********************************************** 
-- *        Monitor ASIC / IC           * 
-- ********************************************** 
-- Monitor ASIC / IC Failure Deasserted 
    IntelligentServerMonitoASICFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Monitor ASIC / IC Failure Deasserted"
        --#SEVERITY INFORMATION
        ::= 2491392
    IntelligentServerMonitoASICFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Monitor ASIC / IC Failure Deasserted"
        --#SEVERITY INFORMATION
        ::= { IntelligentServerServerTRAPObject 2491392 }

-- Monitor ASIC / IC Failure Asserted 
    IntelligentServerMonitoASICFailureAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Monitor ASIC / IC Failure Asserted"
        --#SEVERITY WARNING
        ::= 2491393
    IntelligentServerMonitoASICFailureAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Monitor ASIC / IC Failure Asserted"
        --#SEVERITY WARNING
        ::= { IntelligentServerServerTRAPObject 2491393 }


-- ********************************************** 
-- *        Management Subsystem Health         * 
-- ********************************************** 
-- Sensor access degraded or unavailable 
    IntelligentServerSensorAccessDegradedOrUnavailable TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Sensor access degraded or unavailable Asserted" 
        --#SEVERITY   WARNING
        ::= 2622464
    IntelligentServerSensorAccessDegradedOrUnavailable-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Sensor access degraded or unavailable Asserted" 
        --#SEVERITY   WARNING
        ::= { IntelligentServerServerTRAPObject 2622464 }
        
-- Sensor access degraded or unavailable 
    IntelligentServerSensorAccessDegradedOrUnavailable TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Sensor access degraded or unavailable Clear" 
        --#SEVERITY   INFORMATION
        ::= 2622592
    IntelligentServerSensorAccessDegradedOrUnavailable-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Sensor access degraded or unavailable Clear" 
        --#SEVERITY   INFORMATION
        ::= { IntelligentServerServerTRAPObject 2622592 }

-- Sensor access degraded or unavailable 
    IntelligentServerSensorAccessDegradedOrUnavailable TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Sensor access degraded or unavailable" 
        --#SEVERITY   WARNING
        ::= 2649856
    IntelligentServerSensorAccessDegradedOrUnavailable-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Sensor access degraded or unavailable" 
        --#SEVERITY   WARNING
        ::= { IntelligentServerServerTRAPObject 2649856 }

-- Controller access degraded or unavailable 
    IntelligentServerControllerAccessDegradedOrUnavailable TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "Controller access degraded or unavailable" 
        --#SEVERITY   INFORMATION
        ::= 2649857
    IntelligentServerControllerAccessDegradedOrUnavailable-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "Controller access degraded or unavailable" 
        --#SEVERITY   INFORMATION
        ::= { IntelligentServerServerTRAPObject 2649857 }

-- Management controller off-line 
    IntelligentServerManagementControllerOffline TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Management controller off-line" 
        --#SEVERITY   INFORMATION
        ::= 2649858
    IntelligentServerManagementControllerOffline-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Management controller off-line" 
        --#SEVERITY   INFORMATION
        ::= { IntelligentServerServerTRAPObject 2649858 }

-- Management controller Unavailable 
    IntelligentServerManagementControllerUnavailable TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Management controller Unavailable" 
        --#SEVERITY   INFORMATION
        ::= 2649859
    IntelligentServerManagementControllerUnavailable-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Management controller Unavailable" 
        --#SEVERITY   INFORMATION
        ::= { IntelligentServerServerTRAPObject 2649859 }

-- Sensor failure 
    IntelligentServerSensorFailure TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Sensor failure"
        --#SEVERITY   INFORMATION
        ::= 2649860
    IntelligentServerSensorFailure-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Sensor failure"
        --#SEVERITY   INFORMATION
        ::= { IntelligentServerServerTRAPObject 2649860 }

-- FRU failure 
    IntelligentServerFRUFailure TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU failure"
        --#SEVERITY   INFORMATION
        ::= 2649861
    IntelligentServerFRUFailure-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU failure"
        --#SEVERITY   INFORMATION
        ::= { IntelligentServerServerTRAPObject 2649861 }

-- Sensor access available 
    IntelligentServerSensorAccessAvailable TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Sensor access Available" 
        --#SEVERITY INFORMATION
        ::= 2649984
    IntelligentServerSensorAccessAvailable-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Sensor access Available" 
        --#SEVERITY INFORMATION
        ::= { IntelligentServerServerTRAPObject 2649984 }

-- Controller access Available 
    IntelligentServerControllerAccessAvailable TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Controller access Available"
        --#SEVERITY INFORMATION
        ::= 2649985
    IntelligentServerControllerAccessAvailable-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Controller access Available"
        --#SEVERITY INFORMATION
        ::= { IntelligentServerServerTRAPObject 2649985 }

-- Management controller online 
    IntelligentServerManagementControllerOnline TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Management controller online"
        --#SEVERITY INFORMATION
        ::= 2649986
    IntelligentServerManagementControllerOnline-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Management controller online"
        --#SEVERITY INFORMATION
        ::= { IntelligentServerServerTRAPObject 2649986 }

-- Management controller Available 
    IntelligentServerManagementControllerAvailable TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Management controller Available" 
        --#SEVERITY INFORMATION
        ::= 2649987
    IntelligentServerManagementControllerAvailable-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Management controller Available" 
        --#SEVERITY INFORMATION
        ::= { IntelligentServerServerTRAPObject 2649987 }

-- Sensor failure Deasserted 
    IntelligentServerSensorFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Sensor failure Deasserted" 
        --#SEVERITY INFORMATION
        ::= 2649988
    IntelligentServerSensorFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Sensor failure Deasserted" 
        --#SEVERITY INFORMATION
        ::= { IntelligentServerServerTRAPObject 2649988 }

-- FRU failure Deasserted 
    IntelligentServerFRUFailureDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU failure Deasserted" 
        --#SEVERITY INFORMATION
        ::= 2649989
    IntelligentServerFRUFailureDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU failure Deasserted" 
        --#SEVERITY INFORMATION
        ::= { IntelligentServerServerTRAPObject 2649989 }

-- ********************************************** 
-- *        Battery         * 
-- ********************************************** 

-- Battery low 
    IntelligentServerBatteryLowAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Battery low" 
        --#SEVERITY WARNING
        ::= 2715392
    IntelligentServerBatteryLowAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Battery low" 
        --#SEVERITY WARNING
        ::= { IntelligentServerServerTRAPObject 2715392 }

-- Battery failed 
    IntelligentServerBatteryFailed TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Battery Failed" 
        --#SEVERITY CRITICAL
        ::= 2715393
    IntelligentServerBatteryFailed-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Battery Failed" 
        --#SEVERITY CRITICAL
        ::= { IntelligentServerServerTRAPObject 2715393 }

-- Battery presence detected 
    IntelligentServerBatteryPresenceDetected TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Battery presence detected"
        --#SEVERITY INFORMATION
        ::= 2715394
    IntelligentServerBatteryPresenceDetected-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Battery presence detected"
        --#SEVERITY INFORMATION
        ::= { IntelligentServerServerTRAPObject 2715394 }

-- ********************************************** 
-- *        Session Audit           * 
-- ********************************************** 

-- Session Activated 
    IntelligentServerSessionActivated TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Session Activated"
        --#SEVERITY INFORMATION
        ::= 2780928
    IntelligentServerSessionActivated-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Session Activated"
        --#SEVERITY INFORMATION
        ::= { IntelligentServerServerTRAPObject 2780928 }

-- Session Deactivated 
    IntelligentServerSessionDeactivated TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Session Deactivated" 
        --#SEVERITY WARNING
        ::= 2780929
    IntelligentServerSessionDeactivated-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Session Deactivated" 
        --#SEVERITY WARNING
        ::= { IntelligentServerServerTRAPObject 2780929 }

-- Session Invalid Username or Password 
    IntelligentServerSessionInvalidUsernameOrPassword TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Session Invalid Username or Password"
        --#SEVERITY WARNING
        ::= 2780930
    IntelligentServerSessionInvalidUsernameOrPassword-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Session Invalid Username or Password"
        --#SEVERITY WARNING
        ::= { IntelligentServerServerTRAPObject 2780930 }

-- Session Invalid password disable 
    IntelligentServerSessionUserAccessDisabled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "A user's access has been disabled due to a series of bad password attempts" 
        --#SEVERITY WARNING
        ::= 2780931
    IntelligentServerSessionUserAccessDisabled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "A user's access has been disabled due to a series of bad password attempts" 
        --#SEVERITY WARNING
        ::= { IntelligentServerServerTRAPObject 2780931 }

-- ********************************************** 
-- *        Version Change          * 
-- ********************************************** 

-- Hardware Version change detected 
    IntelligentServerHardwareVersionChangeDetected TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hardware Version change detected with associated Entity"
        --#SEVERITY INFORMATION
        ::= 2846464
    IntelligentServerHardwareVersionChangeDetected-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hardware Version change detected with associated Entity"
        --#SEVERITY INFORMATION
        ::= { IntelligentServerServerTRAPObject 2846464 }

-- Firmware or Software version change detected 
    IntelligentServerFirmwareOrSoftwareVersionChangeDetected TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Firmware or Software version change detected with associated Entity" 
        --#SEVERITY INFORMATION
        ::= 2846465
    IntelligentServerFirmwareOrSoftwareVersionChangeDetected-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Firmware or Software version change detected with associated Entity" 
        --#SEVERITY INFORMATION
        ::= { IntelligentServerServerTRAPObject 2846465 }

-- Hardware Incombabaility detected 
    IntelligentServerHardwareVersionIncombabailityDetected TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hardware Incombabaility detected with associated Entity"
        --#SEVERITY INFORMATION
        ::= 2846466
    IntelligentServerHardwareVersionIncombabailityDetected-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hardware Incombabaility detected with associated Entity"
        --#SEVERITY INFORMATION
        ::= { IntelligentServerServerTRAPObject 2846466 }

-- Firmware Or Software Version Incompatibility detected 
    IntelligentServerFirmwareOrSoftwareVersionIncompatibilityDetected TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Firmware Or Software Version Incompatibility detected with associated Entity" 
        --#SEVERITY INFORMATION
        ::= 2846467
    IntelligentServerFirmwareOrSoftwareVersionIncompatibilityDetected-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Firmware Or Software Version Incompatibility detected with associated Entity" 
        --#SEVERITY INFORMATION
        ::= { IntelligentServerServerTRAPObject 2846467 }

-- Entity is of an invalid or unsupported hardware version 
    IntelligentServerEntityInvalidOrUnsupportedHardware  TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Entity is of an invalid or unsupported hardware version" 
        --#SEVERITY INFORMATION
        ::= 2846468
    IntelligentServerEntityInvalidOrUnsupportedHardware-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Entity is of an invalid or unsupported hardware version" 
        --#SEVERITY INFORMATION
        ::= { IntelligentServerServerTRAPObject 2846468 }

-- Entity contains an invalid or unsupported firmware or software version 
    IntelligentServerEntityInvalidOrUnsupportedSwOrFw TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Entity contains an invalid or unsupported firmware or software version" 
        --#SEVERITY INFORMATION
        ::= 2846469
    IntelligentServerEntityInvalidOrUnsupportedSwOrFw-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Entity contains an invalid or unsupported firmware or software version" 
        --#SEVERITY INFORMATION
        ::= { IntelligentServerServerTRAPObject 2846469 }

-- Hardware Change detected with associated Entity was successful 
    IntelligentServerHardwareChangeSuccessful TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hardware Change detected with associated Entity was successful" 
        --#SEVERITY INFORMATION
        ::= 2846470
    IntelligentServerHardwareChangeSuccessful-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hardware Change detected with associated Entity was successful" 
        --#SEVERITY INFORMATION
        ::= { IntelligentServerServerTRAPObject 2846470 }

-- Software or F/W Change detected with associated Entity was successful. 
    IntelligentServerSwOrFwChangeSuccessful TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Software or F/W Change detected with associated Entity was successful." 
        --#SEVERITY INFORMATION
        ::= 2846471
    IntelligentServerSwOrFwChangeSuccessful-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Software or F/W Change detected with associated Entity was successful." 
        --#SEVERITY INFORMATION
        ::= { IntelligentServerServerTRAPObject 2846471 }
 
 -- Hardware Change detected with associated Entity was not successful 
     IntelligentServerHardwareChangeNotSuccessful TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Hardware Change detected with associated Entity was not successful" 
        --#SEVERITY INFORMATION
        ::= 2846598
    IntelligentServerHardwareChangeNotSuccessful-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Hardware Change detected with associated Entity was not successful" 
        --#SEVERITY INFORMATION
        ::= { IntelligentServerServerTRAPObject 2846598 }

-- Software or F/W Change detected with associated Entity was not successful. 
    IntelligentServerSwOrFwChangeNotSuccessful TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Software or F/W Change detected with associated Entity was not successful."
        --#SEVERITY INFORMATION
        ::= 2846599
    IntelligentServerSwOrFwChangeNotSuccessful-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Software or F/W Change detected with associated Entity was not successful."
        --#SEVERITY INFORMATION
        ::= { IntelligentServerServerTRAPObject 2846599 }

-- ********************************************** 
-- *        FRU State           * 
-- ********************************************** 

-- FRU Not Installed 
    IntelligentServerFRUNotInstalled TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU Not Installed" 
        --#SEVERITY INFORMATION
        ::= 2912000
    IntelligentServerFRUNotInstalled-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU Not Installed" 
        --#SEVERITY INFORMATION
        ::= { IntelligentServerServerTRAPObject 2912000 }
 
 -- FRU Inactive 
     IntelligentServerFRUInactive TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU Inactive"
        --#SEVERITY INFORMATION
        ::= 2912001
    IntelligentServerFRUInactive-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU Inactive"
        --#SEVERITY INFORMATION
        ::= { IntelligentServerServerTRAPObject 2912001 }
 
 -- FRU Activation Requested 
     IntelligentServerFRUActivationRequested TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU Activation Requested"
        --#SEVERITY INFORMATION
        ::= 2912002
    IntelligentServerFRUActivationRequested-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU Activation Requested"
        --#SEVERITY INFORMATION
        ::= { IntelligentServerServerTRAPObject 2912002 }
 
 -- FRU Not Installed 
     IntelligentServerFRUActivationInProgress TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU Activation In Progress" 
        --#SEVERITY INFORMATION
        ::= 2912003
    IntelligentServerFRUActivationInProgress-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU Activation In Progress" 
        --#SEVERITY INFORMATION
        ::= { IntelligentServerServerTRAPObject 2912003 }

 -- FRU Active 
     IntelligentServerFRUActive TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU Active"
        --#SEVERITY INFORMATION
        ::= 2912004
    IntelligentServerFRUActive-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU Active"
        --#SEVERITY INFORMATION
        ::= { IntelligentServerServerTRAPObject 2912004 }
 
 -- FRU Deactivation Requested 
     IntelligentServerFRUDeactivationRequested TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU Deactivation Requested" 
        --#SEVERITY INFORMATION
        ::= 2912005
    IntelligentServerFRUDeactivationRequested-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU Deactivation Requested" 
        --#SEVERITY INFORMATION
        ::= { IntelligentServerServerTRAPObject 2912005 }
 
 -- FRU Deactivation In Progress 
     IntelligentServerFRUDeactivationInProgress TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU Deactivation In Progress" 
        --#SEVERITY INFORMATION
        ::= 2912006
    IntelligentServerFRUDeactivationInProgress-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU Deactivation In Progress" 
        --#SEVERITY INFORMATION
        ::= { IntelligentServerServerTRAPObject 2912006 }
 
 -- FRU Communication Lost 
     IntelligentServerFRUCommunicationLost TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FRU Communication Lost"
        --#SEVERITY INFORMATION
        ::= 2912007
    IntelligentServerFRUCommunicationLost-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FRU Communication Lost"
        --#SEVERITY INFORMATION
        ::= { IntelligentServerServerTRAPObject 2912007 }

 -- MEM Status
-- Processor MEM Pin Out mem over temp Asserted
    IntelligentServerProcessorMEMPinOutMemOverTempAsserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor MEM Pin Out mem over temp Asserted"
        --#SEVERITY CRITICAL
        ::= 789554
    IntelligentServerProcessorMEMPinOutMemOverTempAsserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor MEM Pin Out mem over temp Asserted"
        --#SEVERITY CRITICAL
        ::= { IntelligentServerServerTRAPObject 789554 }
        
-- Processor MEM Pin Out mem over temp Deasserted
    IntelligentServerProcessorMEMPinOutMemOverTempDeasserted TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Processor MEM Pin Out mem over temp Deasserted"
        --#SEVERITY CRITICAL
        ::= 789682
    IntelligentServerProcessorMEMPinOutMemOverTempDeasserted-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Processor MEM Pin Out mem over temp Deasserted"
        --#SEVERITY CRITICAL
        ::= { IntelligentServerServerTRAPObject 789682 }    
 
--cpu0 ch0
    IntelligentServerMemErrorCPU0CH0DIMM0 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel0 Dimm0 memory Error"
        --#SEVERITY CRITICAL
        ::= 12873728
    IntelligentServerMemErrorCPU0CH0DIMM0-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel0 Dimm0 memory Error"
	    --#SEVERITY CRITICAL
        ::= { IntelligentServerServerTRAPObject 12873728 }

    IntelligentServerMemErrorCPU0CH0DIMM1 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel0 Dimm1 memory Error"
        --#SEVERITY CRITICAL
        ::= 12873729
    IntelligentServerMemErrorCPU0CH0DIMM1-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel0 Dimm1 memory Error"
	    --#SEVERITY CRITICAL
        ::= { IntelligentServerServerTRAPObject 12873729}

    IntelligentServerMemErrorCPU0CH0DIMM2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel0 Dimm2 memory Error" 
        --#SEVERITY CRITICAL
        ::= 12873730
    IntelligentServerMemErrorCPU0CH0DIMM2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel0 Dimm2 memory Error" 
	    --#SEVERITY CRITICAL
        ::= { IntelligentServerServerTRAPObject 12873730}

--cpu0 ch1
    IntelligentServerMemErrorCPU0CH1DIMM0 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel1 Dimm0 memory Error" 
        --#SEVERITY CRITICAL
        ::= 12873732
    IntelligentServerMemErrorCPU0CH1DIMM0-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel1 Dimm0 memory Error" 
	    --#SEVERITY CRITICAL
        ::= { IntelligentServerServerTRAPObject 12873732 }

    IntelligentServerMemErrorCPU0CH1DIMM1 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel1 Dimm1 memory Error"
        --#SEVERITY CRITICAL
        ::= 12873733
    IntelligentServerMemErrorCPU0CH1DIMM1-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel1 Dimm1 memory Error"
	    --#SEVERITY CRITICAL
        ::= { IntelligentServerServerTRAPObject 12873733}

    IntelligentServerMemErrorCPU0CH1DIMM2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel1 Dimm2 memory Error" 
        --#SEVERITY CRITICAL
        ::= 12873734
    IntelligentServerMemErrorCPU0CH1DIMM2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel1 Dimm2 memory Error" 
	    --#SEVERITY CRITICAL
        ::= { IntelligentServerServerTRAPObject 12873734}

--cpu0 ch2
    IntelligentServerMemErrorCPU0CH2DIMM0 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel2 Dimm0 memory Error" 
        --#SEVERITY CRITICAL
        ::= 12873736
    IntelligentServerMemErrorCPU0CH2DIMM0-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel2 Dimm0 memory Error" 
	    --#SEVERITY CRITICAL
        ::= { IntelligentServerServerTRAPObject 12873736 }

    IntelligentServerMemErrorCPU0CH2DIMM1 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel2 Dimm1 memory Error" 
        --#SEVERITY CRITICAL
        ::= 12873737
    IntelligentServerMemErrorCPU0CH2DIMM1-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel2 Dimm1 memory Error" 
	    --#SEVERITY CRITICAL
        ::= { IntelligentServerServerTRAPObject 12873737}

    IntelligentServerMemErrorCPU0CH2DIMM2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel2 Dimm2 memory Error" 
        --#SEVERITY CRITICAL
        ::= 12873738
    IntelligentServerMemErrorCPU0CH2DIMM2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel2 Dimm2 memory Error" 
	    --#SEVERITY CRITICAL
        ::= { IntelligentServerServerTRAPObject 12873738}


--cpu0 ch3
    IntelligentServerMemErrorCPU0CH3DIMM0 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel3 Dimm0 memory Error" 
        --#SEVERITY CRITICAL
        ::= 12873740
    IntelligentServerMemErrorCPU0CH3DIMM0-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel3 Dimm0 memory Error" 
	    --#SEVERITY CRITICAL
        ::= { IntelligentServerServerTRAPObject 12873740 }

    IntelligentServerMemErrorCPU0CH3DIMM1 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel3 Dimm1 memory Error" 
        --#SEVERITY CRITICAL
        ::= 12873741
    IntelligentServerMemErrorCPU0CH3DIMM1-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel3 Dimm1 memory Error" 
	    --#SEVERITY CRITICAL
        ::= { IntelligentServerServerTRAPObject 12873741}


        
    IntelligentServerMemErrorCPU0CH3DIMM2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Channel3 Dimm2 memory Error"
        --#SEVERITY CRITICAL 
        ::= 12873742
    IntelligentServerMemErrorCPU0CH3DIMM2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Channel3 Dimm2 memory Error"
	    --#SEVERITY CRITICAL 
        ::= { IntelligentServerServerTRAPObject 12873742}


--cpu1 ch0
    IntelligentServerMemErrorCPU1CH0DIMM0 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 Channel0 Dimm0 memory Error"
        --#SEVERITY CRITICAL
        ::= 12873744
    IntelligentServerMemErrorCPU1CH0DIMM0-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 Channel0 Dimm0 memory Error"
	    --#SEVERITY CRITICAL
        ::= { IntelligentServerServerTRAPObject 12873744 }

    IntelligentServerMemErrorCPU1CH0DIMM1 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 Channel0 Dimm1 memory Error"
        --#SEVERITY CRITICAL
        ::= 12873745
    IntelligentServerMemErrorCPU1CH0DIMM1-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 Channel0 Dimm1 memory Error"
	    --#SEVERITY CRITICAL
        ::= { IntelligentServerServerTRAPObject 12873745}
    
    IntelligentServerMemErrorCPU1CH0DIMM2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 Channel0 Dimm2 memory Error"
        --#SEVERITY CRITICAL 
        ::= 12873746
    IntelligentServerMemErrorCPU1CH0DIMM2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 Channel0 Dimm2 memory Error"
	    --#SEVERITY CRITICAL 
        ::= { IntelligentServerServerTRAPObject 12873746}
    
--cpu1 ch1
    IntelligentServerMemErrorCPU1CH1DIMM0 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 Channel1 Dimm0 memory Error" 
            --#SEVERITY CRITICAL
        ::= 12873748
    IntelligentServerMemErrorCPU1CH1DIMM0-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 Channel1 Dimm0 memory Error" 
            --#SEVERITY CRITICAL
        ::= { IntelligentServerServerTRAPObject 12873748 }
    
    IntelligentServerMemErrorCPU1CH1DIMM1 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 Channel1 Dimm1 memory Error"
        --#SEVERITY CRITICAL
        ::= 12873749
    IntelligentServerMemErrorCPU1CH1DIMM1-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 Channel1 Dimm1 memory Error"
	    --#SEVERITY CRITICAL
        ::= { IntelligentServerServerTRAPObject 12873749}

    IntelligentServerMemErrorCPU1CH1DIMM2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 Channel1 Dimm2 memory Error" 
        --#SEVERITY CRITICAL
        ::= 12873750
    IntelligentServerMemErrorCPU1CH1DIMM2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 Channel1 Dimm2 memory Error" 
	    --#SEVERITY CRITICAL
        ::= { IntelligentServerServerTRAPObject 12873750}

--cpu1 ch2
    IntelligentServerMemErrorCPU1CH2DIMM0 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 Channel2 Dimm0 memory Error" 
        --#SEVERITY CRITICAL
        ::= 12873752
    IntelligentServerMemErrorCPU1CH2DIMM0-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 Channel2 Dimm0 memory Error" 
	    --#SEVERITY CRITICAL
        ::= { IntelligentServerServerTRAPObject 12873752 }

    IntelligentServerMemErrorCPU1CH2DIMM1 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 Channel2 Dimm1 memory Error" 
        --#SEVERITY CRITICAL
        ::= 12873753
    IntelligentServerMemErrorCPU1CH2DIMM1-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 Channel2 Dimm1 memory Error" 
	    --#SEVERITY CRITICAL
        ::= { IntelligentServerServerTRAPObject 12873753}

    IntelligentServerMemErrorCPU1CH2DIMM2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 Channel2 Dimm2 memory Error" 
        --#SEVERITY CRITICAL
        ::= 12873754
    IntelligentServerMemErrorCPU1CH2DIMM2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 Channel2 Dimm2 memory Error" 
	    --#SEVERITY CRITICAL
        ::= { IntelligentServerServerTRAPObject 12873754}


--cpu1 ch3
    IntelligentServerMemErrorCPU1CH3DIMM0 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "CPU1 Channel3 Dimm0 memory Error" 
        --#SEVERITY CRITICAL
        ::= 12873756
    IntelligentServerMemErrorCPU1CH3DIMM0-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "CPU1 Channel3 Dimm0 memory Error" 
	    --#SEVERITY CRITICAL
        ::= { IntelligentServerServerTRAPObject 12873756 }

    IntelligentServerMemErrorCPU1CH3DIMM1 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "CPU1 Channel3 Dimm1 memory Error" 
        --#SEVERITY CRITICAL
        ::= 12873757
    IntelligentServerMemErrorCPU1CH3DIMM1-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "CPU1 Channel3 Dimm1 memory Error" 
	    --#SEVERITY CRITICAL
        ::= { IntelligentServerServerTRAPObject 12873757}

    IntelligentServerMemErrorCPU1CH3DIMM2 TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "CPU1 Channel3 Dimm2 memory Error" 
        --#SEVERITY CRITICAL
        ::= 12873758
    IntelligentServerMemErrorCPU1CH3DIMM2-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "CPU1 Channel3 Dimm2 memory Error" 
	    --#SEVERITY CRITICAL
        ::= { IntelligentServerServerTRAPObject 12873758}

--oem cpu error
    IntelligentServerCPUErrorCPU0BUSORINTERCONNECTERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Bus and interconnect Error" 
        --#SEVERITY CRITICAL
        ::= 12808192
    IntelligentServerCPUErrorCPU0BUSORINTERCONNECTERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Bus and interconnect Error" 
	    --#SEVERITY CRITICAL
        ::= { IntelligentServerServerTRAPObject 12808192}

    IntelligentServerCPUErrorCPU0L3TAGERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 L3 Tag Error" 
        --#SEVERITY CRITICAL
        ::= 12808193
    IntelligentServerCPUErrorCPU0L3TAGERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 L3 Tag Error" 
	    --#SEVERITY CRITICAL
        ::= { IntelligentServerServerTRAPObject 12808193}
    
    IntelligentServerCPUErrorCPU0INTERNALERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU0 Internal Error" 
        --#SEVERITY CRITICAL
        ::= 12808194
    IntelligentServerCPUErrorCPU0INTERNALERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU0 Internal Error" 
	    --#SEVERITY CRITICAL
        ::= { IntelligentServerServerTRAPObject 12808194}

    IntelligentServerCPUErrorCPU1BUSORINTERCONNECTERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 Bus and interconnect Error" 
        --#SEVERITY CRITICAL
        ::= 12808208   
    IntelligentServerCPUErrorCPU1BUSORINTERCONNECTERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 Bus and interconnect Error" 
	    --#SEVERITY CRITICAL
        ::= { IntelligentServerServerTRAPObject 12808208}

    IntelligentServerCPUErrorCPU1L3TAGERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 L3 Tag Error" 
        --#SEVERITY CRITICAL
        ::= 12808209
    IntelligentServerCPUErrorCPU1L3TAGERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 L3 Tag Error" 
	    --#SEVERITY CRITICAL
        ::= { IntelligentServerServerTRAPObject 12808209}

    IntelligentServerCPUErrorCPU1INTERNALERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU1 Internal Error" 
        --#SEVERITY CRITICAL
        ::= 12808210
    IntelligentServerCPUErrorCPU1INTERNALERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU1 Internal Error" 
	    --#SEVERITY CRITICAL
        ::= { IntelligentServerServerTRAPObject 12808210}
    
    IntelligentServerCPUErrorCPU2BUSORINTERCONNECTERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU2 Bus and interconnect Error" 
        --#SEVERITY CRITICAL
        ::= 12808224
    IntelligentServerCPUErrorCPU2BUSORINTERCONNECTERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU2 Bus and interconnect Error" 
	    --#SEVERITY CRITICAL
        ::= { IntelligentServerServerTRAPObject 12808224}

    IntelligentServerCPUErrorCPU2L3TAGERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "CPU2 L3 Tag Error" 
        --#SEVERITY CRITICAL
        ::= 12808225
    IntelligentServerCPUErrorCPU2L3TAGERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "CPU2 L3 Tag Error" 
	    --#SEVERITY CRITICAL
        ::= { IntelligentServerServerTRAPObject 12808225}

    IntelligentServerCPUErrorCPU2INTERNALERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU2 Internal Error" 
        --#SEVERITY CRITICAL
        ::= 12808226
    IntelligentServerCPUErrorCPU2INTERNALERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU2 Internal Error" 
	    --#SEVERITY CRITICAL
        ::= { IntelligentServerServerTRAPObject 12808226}

    IntelligentServerCPUErrorCPU3BUSORINTERCONNECTERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject 
        DESCRIPTION
            "CPU3 Bus and interconnect Error" 
        --#SEVERITY CRITICAL
        ::= 12808240
    IntelligentServerCPUErrorCPU3BUSORINTERCONNECTERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current 
        DESCRIPTION
            "CPU3 Bus and interconnect Error" 
	    --#SEVERITY CRITICAL
        ::= { IntelligentServerServerTRAPObject 12808240}

    IntelligentServerCPUErrorCPU3L3TAGERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU3 L3 Tag Error" 
        --#SEVERITY CRITICAL
        ::= 12808241
    IntelligentServerCPUErrorCPU3L3TAGERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU3 L3 Tag Error" 
	    --#SEVERITY CRITICAL
        ::= { IntelligentServerServerTRAPObject 12808241}

    IntelligentServerCPUErrorCPU3INTERNALERROR TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPU3 Internal Error" 
        --#SEVERITY CRITICAL
        ::= 12808242
    IntelligentServerCPUErrorCPU3INTERNALERROR-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPU3 Internal Error" 
	    --#SEVERITY CRITICAL
        ::= { IntelligentServerServerTRAPObject 12808242}        

-- ********************************************** 
-- *        ISFDS           * 
-- ********************************************** 
-- ISFDS Success
    IntelligentServerISFDSSuccess TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "ISFDS Success"
        --#SEVERITY INFORMATION
        ::= 14299648
    IntelligentServerISFDSSuccess-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "ISFDS Success"
        --#SEVERITY INFORMATION
        ::= { IntelligentServerServerTRAPObject 14299648 }

-- ISFDS Failure
    IntelligentServerISFDSFailure TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "ISFDS Failure"
        --#SEVERITY INFORMATION
        ::= 14299649
    IntelligentServerISFDSFailure-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "ISFDS Failure"
        --#SEVERITY INFORMATION
        ::= { IntelligentServerServerTRAPObject 14299649 }
-- SYS Error Ierr Assert
    IntelligentServerSYSErrorIerr TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Sys Error Ierr Assert"
        --#SEVERITY INFORMATION
        ::= 1381682
    IntelligentServerSYSErrorIerr-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Sys Error Ierr Assert"
        --#SEVERITY INFORMATION
        ::= { IntelligentServerServerTRAPObject 1381682 }
-- SYS Error Ierr Deassert
    IntelligentServerSYSErrorIerrDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Sys Error Ierr Deassert"
        --#SEVERITY INFORMATION
        ::= 1381810
    IntelligentServerSYSErrorIerrDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Sys Error Ierr Deassert"
        --#SEVERITY INFORMATION
        ::= { IntelligentServerServerTRAPObject 1381810 }
-- ********************************************** 
-- *        HYPERCARD           * 
-- ********************************************** 
-- Caterr
    IntelligentServerHYPERCARDCaterrAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Caterr"
        --#SEVERITY WARNING
        ::= 12611328
    IntelligentServerHYPERCARDCaterrAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Caterr"
        --#SEVERITY WARNING
        ::= { IntelligentServerServerTRAPObject 12611328 }
    IntelligentServerHYPERCARDCaterrDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Caterr"
        --#SEVERITY WARNING
        ::= 12611456
    IntelligentServerHYPERCARDCaterrDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Caterr"
        --#SEVERITY WARNING
        ::= { IntelligentServerServerTRAPObject 12611456 }

-- ERR0
    IntelligentServerHYPERCARDERR0Assert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "ERR0"
        --#SEVERITY WARNING
        ::= 12611329
    IntelligentServerHYPERCARDERR0Assert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "ERR0"
        --#SEVERITY WARNING
        ::= { IntelligentServerServerTRAPObject 12611329 }
        
	IntelligentServerHYPERCARDERR0Deassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "ERR0"
        --#SEVERITY WARNING
        ::= 12611457
    IntelligentServerHYPERCARDERR0Deassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "ERR0"
        --#SEVERITY WARNING
        ::= { IntelligentServerServerTRAPObject 12611457 }

-- ERR1
    IntelligentServerHYPERCARDERR1Assert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "ERR1"
        --#SEVERITY WARNING
        ::= 12611330
    IntelligentServerHYPERCARDERR1Assert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "ERR1"
        --#SEVERITY WARNING
        ::= { IntelligentServerServerTRAPObject 12611330 }
        
    IntelligentServerHYPERCARDERR1Deassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "ERR1"
        --#SEVERITY WARNING
        ::= 12611458
    IntelligentServerHYPERCARDERR1Deassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "ERR1"
        --#SEVERITY WARNING
        ::= { IntelligentServerServerTRAPObject 12611458 }

-- ERR2
    IntelligentServerHYPERCARDERR2Assert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "ERR2"
        --#SEVERITY WARNING
        ::= 12611331
    IntelligentServerHYPERCARDERR2Assert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "ERR2"
        --#SEVERITY WARNING
        ::= { IntelligentServerServerTRAPObject 12611331 }
        
    IntelligentServerHYPERCARDERR2Deassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "ERR2"
        --#SEVERITY WARNING
        ::= 12611459
    IntelligentServerHYPERCARDERR2Deassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "ERR2"
        --#SEVERITY WARNING
        ::= { IntelligentServerServerTRAPObject 12611459 }

-- FIVR Fault
    IntelligentServerHYPERCARDFIVRFaultAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FIVR Fault"
        --#SEVERITY WARNING
        ::= 12611332
    IntelligentServerHYPERCARDFIVRFaultAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FIVR Fault"
        --#SEVERITY WARNING
        ::= { IntelligentServerServerTRAPObject 12611332 }
        
    IntelligentServerHYPERCARDFIVRFaultDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FIVR Fault"
        --#SEVERITY WARNING
        ::= 12611460
    IntelligentServerHYPERCARDFIVRFaultDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FIVR Fault"
        --#SEVERITY WARNING
        ::= { IntelligentServerServerTRAPObject 12611460 }
    

-- SOC Thermaltrip
    IntelligentServerHYPERCARDSOCThermaltripAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SOC Thermaltrip"
        --#SEVERITY WARNING
        ::= 12611333
    IntelligentServerHYPERCARDSOCThermaltripAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SOC Thermaltrip"
        --#SEVERITY WARNING
        ::= { IntelligentServerServerTRAPObject 12611333 }
    IntelligentServerHYPERCARDSOCThermaltripDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SOC Thermaltrip"
        --#SEVERITY WARNING
        ::= 12611461
    IntelligentServerHYPERCARDSOCThermaltripDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SOC Thermaltrip"
        --#SEVERITY WARNING
        ::= { IntelligentServerServerTRAPObject 12611461 }
    

-- Prohot
    IntelligentServerHYPERCARDProhotAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Prohot"
        --#SEVERITY WARNING
        ::= 12611334
    IntelligentServerHYPERCARDProhotAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Prohot"
        --#SEVERITY WARNING
        ::= { IntelligentServerServerTRAPObject 12611334 }
    IntelligentServerHYPERCARDProhotDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Prohot"
        --#SEVERITY WARNING
        ::= 12611462
    IntelligentServerHYPERCARDProhotDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Prohot"
        --#SEVERITY WARNING
        ::= { IntelligentServerServerTRAPObject 12611462 }
    

-- SOC VR Hot
    IntelligentServerHYPERCARDSOCVRHotAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SOC VR Hot"
        --#SEVERITY WARNING
        ::= 12611335
    IntelligentServerHYPERCARDSOCVRHotAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SOC VR Hot"
        --#SEVERITY WARNING
        ::= { IntelligentServerServerTRAPObject 12611335 }
        
    IntelligentServerHYPERCARDSOCVRHotDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SOC VR Hot"
        --#SEVERITY WARNING
        ::= 12611463
    IntelligentServerHYPERCARDSOCVRHotDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SOC VR Hot"
        --#SEVERITY WARNING
        ::= { IntelligentServerServerTRAPObject 12611463 }

-- MultiBit ECC MemoryError
    IntelligentServerHYPERCARDMultiBitECCMemoryErrorAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "MultiBit ECC MemoryError"
        --#SEVERITY WARNING
        ::= 12611336
    IntelligentServerHYPERCARDMultiBitECCMemoryErrorAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "MultiBit ECC MemoryError"
        --#SEVERITY WARNING
        ::= { IntelligentServerServerTRAPObject 12611336 }
    
    IntelligentServerHYPERCARDMultiBitECCMemoryErrorDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "MultiBit ECC MemoryError"
        --#SEVERITY WARNING
        ::= 12611464
    IntelligentServerHYPERCARDMultiBitECCMemoryErrorDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "MultiBit ECC MemoryError"
        --#SEVERITY WARNING
        ::= { IntelligentServerServerTRAPObject 12611464 }

-- PERR
    IntelligentServerHYPERCARDPERRAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "PERR"
        --#SEVERITY WARNING
        ::= 12611337
    IntelligentServerHYPERCARDPERRAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "PERR"
        --#SEVERITY WARNING
        ::= { IntelligentServerServerTRAPObject 12611337 }
	
	IntelligentServerHYPERCARDPERRDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "PERR"
        --#SEVERITY WARNING
        ::= 12611465
    IntelligentServerHYPERCARDPERRDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "PERR"
        --#SEVERITY WARNING
        ::= { IntelligentServerServerTRAPObject 12611465 }
-- SERR
    IntelligentServerHYPERCARDSERRAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SERR"
        --#SEVERITY WARNING
        ::= 12611338
    IntelligentServerHYPERCARDSERRAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SERR"
        --#SEVERITY WARNING
        ::= { IntelligentServerServerTRAPObject 12611338 }
        
    IntelligentServerHYPERCARDSERRDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SERR"
        --#SEVERITY WARNING
        ::= 12611466
    IntelligentServerHYPERCARDSERRDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SERR"
        --#SEVERITY WARNING
        ::= { IntelligentServerServerTRAPObject 12611466 }

-- FPGA Thermaltrip
    IntelligentServerHYPERCARDFPGAThermaltripAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FPGA Thermaltrip"
        --#SEVERITY WARNING
        ::= 12611339
    IntelligentServerHYPERCARDFPGAThermaltripAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FPGA Thermaltrip"
        --#SEVERITY WARNING
        ::= { IntelligentServerServerTRAPObject 12611339 }
    
    IntelligentServerHYPERCARDFPGAThermaltripDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FPGA Thermaltrip"
        --#SEVERITY WARNING
        ::= 12611467
    IntelligentServerHYPERCARDFPGAThermaltripDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FPGA Thermaltrip"
        --#SEVERITY WARNING
        ::= { IntelligentServerServerTRAPObject 12611467 }

-- FPGA Hot
    IntelligentServerHYPERCARDFPGAHotAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FPGA Hot"
        --#SEVERITY WARNING
        ::= 12611340
    IntelligentServerHYPERCARDFPGAHotAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FPGA Hot"
        --#SEVERITY WARNING
        ::= { IntelligentServerServerTRAPObject 12611340 }
     
    IntelligentServerHYPERCARDFPGAHotDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FPGA Hot"
        --#SEVERITY WARNING
        ::= 12611468
    IntelligentServerHYPERCARDFPGAHotDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FPGA Hot"
        --#SEVERITY WARNING
        ::= { IntelligentServerServerTRAPObject 12611468 }

-- FPGA VR Hot
    IntelligentServerHYPERCARDFPGAVRHotAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FPGA VR Hot"
        --#SEVERITY WARNING
        ::= 12611341
    IntelligentServerHYPERCARDFPGAVRHotAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FPGA VR Hot"
        --#SEVERITY WARNING
        ::= { IntelligentServerServerTRAPObject 12611341 }
        
    IntelligentServerHYPERCARDFPGAVRHotDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FPGA VR Hot"
        --#SEVERITY WARNING
        ::= 12611469
    IntelligentServerHYPERCARDFPGAVRHotDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FPGA VR Hot"
        --#SEVERITY WARNING
        ::= { IntelligentServerServerTRAPObject 12611469 }

-- SOC Mem Hot
    IntelligentServerHYPERCARDSOCMemHotAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SOC Mem Hot"
        --#SEVERITY WARNING
        ::= 12611342
    IntelligentServerHYPERCARDSOCMemHotAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SOC Mem Hot"
        --#SEVERITY WARNING
        ::= { IntelligentServerServerTRAPObject 12611342 }
      
    IntelligentServerHYPERCARDSOCMemHotDeassert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "SOC Mem Hot"
        --#SEVERITY WARNING
        ::= 12611470
    IntelligentServerHYPERCARDSOCMemHotDeassert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "SOC Mem Hot"
        --#SEVERITY WARNING
        ::= { IntelligentServerServerTRAPObject 12611470 }
      
-- BMC FW UPDATE UPGRADE IMAGE
    IntelligentServerBMCFWUPDATEUPGRADEIMAGE TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "BMC FW UPDATE UPGRADE IMAGE"
        --#SEVERITY INFORMATION
        ::= 13762560
    IntelligentServerBMCFWUPDATEUPGRADEIMAGE-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "BMC FW UPDATE UPGRADE IMAGE"
        --#SEVERITY INFORMATION
        ::= { IntelligentServerServerTRAPObject 13762560 }

-- BIOS FW UPDATE UPGRADE IMAGE 
    IntelligentServerBIOSFWUPDATEUPGRADEIMAGE TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "BIOS FW UPDATE UPGRADE IMAGE"
        --#SEVERITY INFORMATION
        ::= 13762561
    IntelligentServerBIOSFWUPDATEUPGRADEIMAGE-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "BIOS FW UPDATE UPGRADE IMAGE"
        --#SEVERITY INFORMATION
        ::= { IntelligentServerServerTRAPObject 13762561 }

-- BMC FW UPDATE IMAGE VERRIFY
    IntelligentServerBMCFWUPDATEIMAGEVERRIFY TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "BMC FW UPDATE IMAGE VERRIFY"
        --#SEVERITY INFORMATION
        ::= 13762566
    IntelligentServerBMCFWUPDATEIMAGEVERRIFY-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "BMC FW UPDATE IMAGE VERRIFY"
        --#SEVERITY INFORMATION
        ::= { IntelligentServerServerTRAPObject 13762566 }
        
-- BMC FW UPDATE ROLL BACK IMAGE
    IntelligentServerBMCFWUPDATEROLLBACKIMAGE TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "BMC FW UPDATE ROLL BACK IMAGE"
        --#SEVERITY INFORMATION
        ::= 13762568
    IntelligentServerBMCFWUPDATEROLLBACKIMAGE-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "BMC FW UPDATE ROLL BACK IMAGE"
        --#SEVERITY INFORMATION
        ::= { IntelligentServerServerTRAPObject 13762568 }

-- BIOS FW UPDATE IMAGE VERRIFY
    IntelligentServerBIOSFWUPDATEIMAGEVERRIFY TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "BIOS FW UPDATE IMAGE VERRIFY"
        --#SEVERITY INFORMATION
        ::= 13762567
    IntelligentServerBIOSFWUPDATEIMAGEVERRIFY-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "BIOS FW UPDATE IMAGE VERRIFY"
        --#SEVERITY INFORMATION
        ::= { IntelligentServerServerTRAPObject 13762567 }

-- FPGA FW UPDATE IMAGE VERRIFY
    IntelligentServerFPGAFWUPDATEIMAGEVERRIFY TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FPGA FW UPDATE IMAGE VERRIFY"
        --#SEVERITY INFORMATION
        ::= 13762570
    IntelligentServerFPGAFWUPDATEIMAGEVERRIFY-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FPGA FW UPDATE IMAGE VERRIFY"
        --#SEVERITY INFORMATION
        ::= { IntelligentServerServerTRAPObject 13762570 }

-- FPGA FW UPDATE UPGRADE IMAGE 
    IntelligentServerFPGAFWUPDATEUPGRADEIMAGE TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "FPGA FW UPDATE UPGRADE IMAGE"
        --#SEVERITY INFORMATION
        ::= 13762565
    IntelligentServerFPGAFWUPDATEUPGRADEIMAGE-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "FPGA FW UPDATE UPGRADE IMAGE"
        --#SEVERITY INFORMATION
        ::= { IntelligentServerServerTRAPObject 13762565 }

-- CPLD FW UPDATE IMAGE VERRIFY
    IntelligentServerCPLDFWUPDATEIMAGEVERRIFY TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPLD FW UPDATE IMAGE VERRIFY"
        --#SEVERITY INFORMATION
        ::= 13762569
    IntelligentServerCPLDFWUPDATEIMAGEVERRIFY-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPLD FW UPDATE IMAGE VERRIFY"
        --#SEVERITY INFORMATION
        ::= { IntelligentServerServerTRAPObject 13762569 }

-- CPLD FW UPDATE UPGRADE IMAGE 
    IntelligentServerCPLDFWUPDATEUPGRADEIMAGE TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "CPLD FW UPDATE UPGRADE IMAGE"
        --#SEVERITY INFORMATION
        ::= 13762562
    IntelligentServerCPLDFWUPDATEUPGRADEIMAGE-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "CPLD FW UPDATE UPGRADE IMAGE"
        --#SEVERITY INFORMATION
        ::= { IntelligentServerServerTRAPObject 13762562 }

-- PSU FW UPDATE IMAGE VERRIFY
    IntelligentServerPSUFWUPDATEIMAGEVERRIFY TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "PSU FW UPDATE IMAGE VERRIFY"
        --#SEVERITY INFORMATION
        ::= 13762571
    IntelligentServerPSUFWUPDATEIMAGEVERRIFY-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "PSU FW UPDATE IMAGE VERRIFY"
        --#SEVERITY INFORMATION
        ::= { IntelligentServerServerTRAPObject 13762571 }

-- PSU FW UPDATE UPGRADE IMAGE 
    IntelligentServerPSUFWUPDATEUPGRADEIMAGE TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "PSU FW UPDATE UPGRADE IMAGE"
        --#SEVERITY INFORMATION
        ::= 13762563
    IntelligentServerPSUFWUPDATEUPGRADEIMAGE-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "PSU FW UPDATE UPGRADE IMAGE"
        --#SEVERITY INFORMATION
        ::= { IntelligentServerServerTRAPObject 13762563 }
-- RAID LD DEGRADED
    IntelligentServerRaidLdDegradedAssert TRAP-TYPE
        OBJECTS { altHostLocation, altTrapTime, altSysManufacture, altSysModel, altSensorName, altSensorType, altSensorReading, altSensorThreshold, altHostContact, altBMCHostName, altSysName, altSpTxtId, altPriority, altEventAssertOrDeassert }
        STATUS current
        ENTERPRISE IntelligentServerServerTRAPObject
        DESCRIPTION
            "Raid Ld Degraded Assert"
        --#SEVERITY INFORMATION
        ::= 13697806
    IntelligentServerRaidLdDegradedAssert-V2cV3 NOTIFICATION-TYPE
        OBJECTS { altHostLocation, altTrapTime, altSysManufacture, altSysModel, altSensorName, altSensorType, altSensorReading, altSensorThreshold, altHostContact, altBMCHostName, altSysName, altSpTxtId, altPriority, altEventAssertOrDeassert }
        STATUS current
        DESCRIPTION
            "Raid Ld Degraded Assert"
        --#SEVERITY INFORMATION
        ::= { IntelligentServerServerTRAPObject 13697806 }

    IntelligentServerRaidLdDegradedDeassert TRAP-TYPE
        OBJECTS { altHostLocation, altTrapTime, altSysManufacture, altSysModel,altHostContact, altBMCHostName, altSysName, altSpTxtId, altPriority, altEventDescription,  altEventAssertOrDeassert }
        STATUS current
        ENTERPRISE IntelligentServerServerTRAPObject
        DESCRIPTION
            "Raid Ld Degraded Deassert"
        --#SEVERITY INFORMATION
        ::= 13697934
    IntelligentServerRaidLdDegradedDeassert-V2cV3 NOTIFICATION-TYPE
        OBJECTS { altHostLocation, altTrapTime, altSysManufacture, altSysModel, altHostContact, altBMCHostName, altSysName, altSpTxtId, altPriority,altEventDescription,  altEventAssertOrDeassert }
        STATUS current
        DESCRIPTION
            "Raid Ld Degraded Deassert"
        --#SEVERITY INFORMATION
        ::= { IntelligentServerServerTRAPObject 13697934 }
END
