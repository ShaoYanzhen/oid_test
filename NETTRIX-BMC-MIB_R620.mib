--  $Id: NETTRIX-BMC-MIB.mib$
--	Version: V013
--
--  DESCRIPTION
--      This MIB file defines objects that can be managed on
--      Nettrix server BMCs.
--
--  LAST-UPDATED
--      20200305 - Initial Version
--
--  ORGANIZATION
--      Dawning Information Ltd.
--
--  CONTACT-INFO
--      E-mail: bear.zhang@nettrix.com.cn

-- Define MIB Name 
     NETTRIXSERVERMGMT-MIB     DEFINITIONS         ::= BEGIN


-- IMPORTS Statement 
IMPORTS 
    enterprises, IpAddress, Gauge, TimeTicks  ,NetworkAddress   
        FROM RFC1155-SMI

    MODULE-IDENTITY,OBJECT-IDENTITY,NOTIFICATION-TYPE,
    OBJECT-TYPE,Unsigned32,Integer32,Counter32
        FROM SNMPv2-SMI
     
    DisplayString, TruthValue
        FROM SNMPv2-TC;

-- MODULE-IDENTITY Statement




-- NODE DEfinitions Statement

    nettrix OBJECT IDENTIFIER             ::=  { enterprises 55380 }
    equipment OBJECT IDENTIFIER         ::=  { nettrix 1 }
    server OBJECT IDENTIFIER            ::=  { equipment 1 }
    management OBJECT IDENTIFIER        ::=  { server 1 }
    bmc OBJECT IDENTIFIER               ::=  { management 1 }
   
    --====== BMC Node ========

--  ************************system**********************
    

    system OBJECT IDENTIFIER            ::=  { bmc 1 }

    fwVersion OBJECT-TYPE
	    SYNTAX  DisplayString
	    ACCESS  read-only
	    STATUS  mandatory
	    DESCRIPTION "BMC firmware version"
	    ::= { system 1 }

    systemProductType OBJECT-TYPE
	    SYNTAX  DisplayString
	    ACCESS  read-only
	    STATUS  mandatory
	    DESCRIPTION "Product Type"
	    ::= { system 2 }

    systemProductName OBJECT-TYPE
	    SYNTAX  DisplayString
	    ACCESS  read-only
	    STATUS  mandatory
	    DESCRIPTION "System Product Name"
	    ::= { system 3 }
	
	  systemProductSN OBJECT-TYPE
	    SYNTAX  DisplayString
	    ACCESS  read-only
	    STATUS  mandatory
	    DESCRIPTION "System Product Serial Number"
	    ::= { system 4 }
	        
    systemPower OBJECT-TYPE
	    SYNTAX  DisplayString
	    ACCESS  read-write
	    STATUS  mandatory
	    DESCRIPTION 
	    "System Power
	    Power On or Off the system.    
				 0  - Power off	
				 1  - Power on	 
				 2  - Power Cycle   
				 3  - Hard Reset
				 5  - ACPI Shut Down       "
	    ::= { system 5 }

    systemStatus OBJECT-TYPE
	    SYNTAX  INTEGER
	    ACCESS  read-only
	    STATUS  mandatory
	    DESCRIPTION "System Status"
	    ::= { system 6 }
	    
	  systemTime OBJECT-TYPE
	    SYNTAX  DisplayString
	    ACCESS  read-only
	    STATUS  mandatory
	    DESCRIPTION "System Time"
	    ::= { system 7 }
	    
	  systemTimeZone OBJECT-TYPE
	    SYNTAX  DisplayString
	    ACCESS  read-only
	    STATUS  mandatory
	    DESCRIPTION "System Time Zone"
	    ::= { system 8 }
	    
	  systemGuid OBJECT-TYPE
	    SYNTAX  DisplayString
	    ACCESS  read-only
	    STATUS  mandatory
	    DESCRIPTION "System GUID"
	    ::= { system 9 }

		systemPowerPolicy OBJECT-TYPE   
			SYNTAX DisplayString
			ACCESS read-write
			STATUS current
			DESCRIPTION
				"  0  - Always Off
				   1  - Last State
				   2  - Always ON  "
			::= { system 10 }	

		systemBiosFirstBootDevice OBJECT-TYPE   
			SYNTAX DisplayString
			ACCESS read-write
			STATUS current
			DESCRIPTION
				"  4  - pxe
				   8  - disk
				   20 - cdrom
				   24 - bios  "
			::= { system 11 }	
			
		systemIDIdentify OBJECT-TYPE   
			SYNTAX DisplayString
			ACCESS read-write
			STATUS current
			DESCRIPTION
				"systemIDIdentify use to turn on or off ID led. 
				 operation format: <operation>,[time] 
				
				 operation mode:   
				 0  - Force off	
				 1  - Force on
				 2  - Identify Blink Time Seconds
				 3  - Identify Blink Time Hours
				 4  - Identify Blink Time Days          
				 				 
				 When <operation mode> = 0, the [time] is invalid.
				 When <operation mode> = 1, the [time] is invalid.
				 When <operation mode> = 2, the [time] is the ID blink time(seconds).
				 When <operation mode> = 3, the [time] is the ID blink time(hours)
				 When <operation mode> = 4, the [time] is the ID blink time(days)
				 The value is in [1,255], the default is 15 seconds when no time parameter."
			::= { system 12 }
			
		hostName OBJECT-TYPE   
			SYNTAX DisplayString
			ACCESS read-write
			STATUS current
			DESCRIPTION
			"
			"
			::= { system 13 }
			
		bmcReboot OBJECT-TYPE
			SYNTAX INTEGER	   
			MAX-ACCESS read-write
			STATUS current
			DESCRIPTION
				" 1  - reboot bmc
				Reboot the BMC management system.When set, the value is only 1, write only."
			::= { system 14 }	
						
		sysPowerButton OBJECT-TYPE   
			SYNTAX DisplayString
			ACCESS read-write
			STATUS current
			DESCRIPTION
			  " 0 - Enable
			    1 - Disable   "
			::= { system 15 }
			
		systemRealTimePower OBJECT-TYPE
			SYNTAX  DisplayString
			ACCESS  read-only
			STATUS  mandatory
			DESCRIPTION 
			"system real-time power consume"
			::= { system 16 }
			
			
		syncNtpTime OBJECT-TYPE
			SYNTAX  DisplayString
			ACCESS  read-write
			STATUS  mandatory
			DESCRIPTION 
			"Sync Time
			Sync time form ntp serve    
				 0  - everyMinute	
				 1  - everyHour	  
				 2  - everyDay	 
				 3  - everyWeek	 
				 4  - everyMonth	          "
			::= { system 17 }
			
		primaryNtpServerIP OBJECT-TYPE
			SYNTAX  DisplayString
			ACCESS  read-write
			STATUS  mandatory
			DESCRIPTION 
			"Set ntp server address,Please input ntp server address"
			::= { system 18 }
			
		secondaryNtpServerIP OBJECT-TYPE
			SYNTAX  DisplayString
			ACCESS  read-write
			STATUS  mandatory
			DESCRIPTION 
			"Set ntp server address,Please input ntp server address"
			::= { system 19 }

			
			
--  ************************sensor**********************
    sensor OBJECT IDENTIFIER            ::=  { bmc 2 }

    sensorCount OBJECT-TYPE
	    SYNTAX  INTEGER
	    ACCESS  read-only
	    STATUS  mandatory
	    DESCRIPTION "Sensor Count"
	    ::= { sensor 1 }

         -- Sensor Table

    sensorTable OBJECT-TYPE
      SYNTAX  SEQUENCE OF SensorEntry
      ACCESS  not-accessible
      STATUS  mandatory
      ::= { sensor 2 }

        sensorEntry OBJECT-TYPE
          SYNTAX  SensorEntry
          ACCESS  not-accessible
          STATUS  mandatory
          INDEX   { sensorIndex }
          ::= { sensorTable 1 }

        SensorEntry ::= SEQUENCE {
          sensorIndex                   INTEGER,
          sensorName                    DisplayString,
          sensorNumber                  INTEGER,
          sensorType                    DisplayString,
          sensorValue                   DisplayString,
          sensorStatus                  DisplayString,
          thresholdUpperNonRecoverable  DisplayString,
          thresholdUpperCritical        DisplayString,
          thresholdUpperNonCritical     DisplayString,
          thresholdLowerNonCritical     DisplayString,
          thresholdLowerCritical        DisplayString,
          thresholdLowerNonRecoverable  DisplayString }

               sensorIndex OBJECT-TYPE
                       SYNTAX  INTEGER
                       ACCESS  read-only
                       STATUS  mandatory
                       ::=  { sensorEntry 1 }

               sensorName OBJECT-TYPE
                       SYNTAX  DisplayString 
                       ACCESS  read-only
                       STATUS  mandatory
                       ::=  { sensorEntry 2 }
                       
               sensorNumber OBJECT-TYPE
                       SYNTAX  INTEGER
                       ACCESS  read-only
                       STATUS  mandatory
                       ::=  { sensorEntry 3 }

               sensorType OBJECT-TYPE
                       SYNTAX  DisplayString 
                       ACCESS  read-only
                       STATUS  mandatory
                       ::=  { sensorEntry 4 }

               sensorValue OBJECT-TYPE
                       SYNTAX  DisplayString 
                       ACCESS  read-only
                       STATUS  mandatory
                       ::= { sensorEntry 5 }

               sensorStatus OBJECT-TYPE
                       SYNTAX  DisplayString 
                       ACCESS  read-only
                       STATUS  mandatory
                       ::= { sensorEntry 6 }

	             thresholdUpperNonRecoverable OBJECT-TYPE
                       SYNTAX  DisplayString  
                       ACCESS  read-only
                       STATUS  mandatory
                       ::= { sensorEntry 7 }

	             thresholdUpperCritical OBJECT-TYPE
                       SYNTAX  DisplayString  
                       ACCESS  read-only
                       STATUS  mandatory
                       ::= { sensorEntry 8 }

	             thresholdUpperNonCritical OBJECT-TYPE
                       SYNTAX  DisplayString  
                       ACCESS  read-only
                       STATUS  mandatory
                       ::= { sensorEntry 9 }

	             thresholdLowerNonCritical OBJECT-TYPE
                       SYNTAX  DisplayString  
                       ACCESS  read-only
                       STATUS  mandatory
                       ::= { sensorEntry 10 }
	
	             thresholdLowerCritical OBJECT-TYPE
                       SYNTAX  DisplayString  
                       ACCESS  read-only
                       STATUS  mandatory
                       ::= { sensorEntry 11 }

	             thresholdLowerNonRecoverable OBJECT-TYPE
                       SYNTAX  DisplayString  
                       ACCESS  read-only
                       STATUS  mandatory
                       ::= { sensorEntry 12 }



          
          
--  ************************componentInfo**********************     
     
    componentInfo OBJECT IDENTIFIER     ::=  { bmc 4 }

      -- CPU Table

        cpuTable OBJECT-TYPE
        SYNTAX  SEQUENCE OF CpuEntry
        ACCESS  not-accessible
        STATUS  mandatory
        ::= { componentInfo 1 }

            cpuEntry OBJECT-TYPE
              SYNTAX  CpuEntry
              ACCESS  not-accessible
              STATUS  mandatory
              INDEX   { cpuIndex }
              ::= { cpuTable 1 }

            CpuEntry ::= SEQUENCE {
              cpuIndex                                      INTEGER,
              cpuLocation                                   DisplayString,
              cpuPresent                                    DisplayString,   
              cpuBrandName                                  DisplayString,
              cpuFrequency                                  DisplayString,         
              cpuTDP                                        DisplayString,
              cpuMaxCoresThreads                            DisplayString,
              cpuSystemClockSpeed                           DisplayString,
              cpuTurboFrequency                             DisplayString,
              cpuCurrentCoresThreads                        DisplayString,
              cpuL1L2L3CacheInfo                          DisplayString,
              cpuS-Spec                                     DisplayString,
              cpuFamily                                     DisplayString,
              cpuModel                                      DisplayString,
              cpuStepping                                   DisplayString,
              cpuExtFamily                                  DisplayString,
              cpuExtModel                                   DisplayString,          
              cpuUPIFrequency                               DisplayString,
              cpuUPILinkNumber                              DisplayString,
              cpuMaxUPILinkTransferRate                     DisplayString,
              cpuMaxPCIeLinkTransferRate                    DisplayString,
              cpuMaxSupportIntelDCPersistentMemorySize      DisplayString,
              cpuTcase                                      DisplayString,
              cpuFeatures                                   DisplayString             
              
                }

                cpuIndex OBJECT-TYPE
                  SYNTAX  INTEGER
                  ACCESS  read-only
                  STATUS  mandatory
                  ::=  { cpuEntry 1 }

                cpuLocation OBJECT-TYPE
                  SYNTAX  DisplayString 
                  ACCESS  read-only
                  STATUS  mandatory
                  ::=  { cpuEntry 2 }
                  
                cpuPresent OBJECT-TYPE
                  SYNTAX  DisplayString
                  ACCESS  read-only
                  STATUS  mandatory
                  ::=  { cpuEntry 3 }
                 
                cpuBrandName OBJECT-TYPE
                  SYNTAX  DisplayString
                  ACCESS  read-only
                  STATUS  mandatory
                  ::=  { cpuEntry 4 }

                cpuFrequency OBJECT-TYPE
                  SYNTAX  DisplayString
                  ACCESS  read-only
                  STATUS  mandatory
                  ::=  { cpuEntry 5 }

                cpuTDP OBJECT-TYPE
                  SYNTAX  DisplayString 
                  ACCESS  read-only
                  STATUS  mandatory
                  ::=  { cpuEntry 6 }
                  
                cpuMaxCoresThreads OBJECT-TYPE
                  SYNTAX  DisplayString 
                  ACCESS  read-only
                  STATUS  mandatory
                  ::=  { cpuEntry 7 }
                  
                cpuSystemClockSpeed OBJECT-TYPE
                  SYNTAX  DisplayString 
                  ACCESS  read-only
                  STATUS  mandatory
                  ::=  { cpuEntry 8 }
                  
                cpuTurboFrequency OBJECT-TYPE
                  SYNTAX  DisplayString 
                  ACCESS  read-only
                  STATUS  mandatory
                  ::=  { cpuEntry 9 }
                  
                cpuCurrentCoresThreads OBJECT-TYPE
                  SYNTAX  DisplayString 
                  ACCESS  read-only
                  STATUS  mandatory
                  ::=  { cpuEntry 10 }                                    
                  
                cpuL1L2L3CacheInfo OBJECT-TYPE
                  SYNTAX  DisplayString 
                  ACCESS  read-only
                  STATUS  mandatory
                  ::=  { cpuEntry 11 }
                  
                cpuS-Spec OBJECT-TYPE
                  SYNTAX  DisplayString 
                  ACCESS  read-only
                  STATUS  mandatory
                  ::=  { cpuEntry 12 }                  
                  
                cpuFamily OBJECT-TYPE
                  SYNTAX  DisplayString 
                  ACCESS  read-only
                  STATUS  mandatory
                  ::=  { cpuEntry 13 }                  
                  
                cpuModel OBJECT-TYPE
                  SYNTAX  DisplayString 
                  ACCESS  read-only
                  STATUS  mandatory
                  ::=  { cpuEntry 14 }                  
                  
                cpuStepping OBJECT-TYPE
                  SYNTAX  DisplayString 
                  ACCESS  read-only
                  STATUS  mandatory
                  ::=  { cpuEntry 15 }                  
                  
                cpuExtFamily OBJECT-TYPE
                  SYNTAX  DisplayString 
                  ACCESS  read-only
                  STATUS  mandatory
                  ::=  { cpuEntry 16 }                  
                  
                cpuExtModel OBJECT-TYPE
                  SYNTAX  DisplayString 
                  ACCESS  read-only
                  STATUS  mandatory
                  ::=  { cpuEntry 17 }

                cpuUPIFrequency OBJECT-TYPE
                  SYNTAX  DisplayString 
                  ACCESS  read-only
                  STATUS  mandatory
                  ::=  { cpuEntry 18 }

                cpuUPILinkNumber OBJECT-TYPE
                  SYNTAX  DisplayString 
                  ACCESS  read-only
                  STATUS  mandatory
                  ::=  { cpuEntry 19 }

                cpuMaxUPILinkTransferRate OBJECT-TYPE
                  SYNTAX  DisplayString 
                  ACCESS  read-only
                  STATUS  mandatory
                  ::=  { cpuEntry 20 }

                cpuMaxPCIeLinkTransferRate OBJECT-TYPE
                  SYNTAX  DisplayString 
                  ACCESS  read-only
                  STATUS  mandatory
                  ::=  { cpuEntry 21 }

                cpuMaxSupportIntelDCPersistentMemorySize OBJECT-TYPE
                  SYNTAX  DisplayString 
                  ACCESS  read-only
                  STATUS  mandatory
                  ::=  { cpuEntry 22 }

                cpuTcase OBJECT-TYPE
                  SYNTAX  DisplayString 
                  ACCESS  read-only
                  STATUS  mandatory
                  ::=  { cpuEntry 23 }

                cpuFeatures OBJECT-TYPE
                  SYNTAX  DisplayString 
                  ACCESS  read-only
                  STATUS  mandatory
                  ::=  { cpuEntry 24 }




         -- Memory Table

        memoryTable OBJECT-TYPE
          SYNTAX  SEQUENCE OF MemoryEntry
            ACCESS  not-accessible
            STATUS  mandatory
            ::= { componentInfo 2 }

            memoryEntry OBJECT-TYPE
              SYNTAX  MemoryEntry
              ACCESS  not-accessible
              STATUS  mandatory
              INDEX   { memoryIndex }
              ::= { memoryTable 1 }

            MemoryEntry ::= SEQUENCE {
              memoryIndex               INTEGER,
              memoryLocation            DisplayString,
              memoryPresent             DisplayString,
              memoryVendor              DisplayString,
              memoryPN                  DisplayString,
              memorySN                  DisplayString,
              memoryDRAMType            DisplayString,
              memoryModule              DisplayString,
              memoryType                DisplayString,
              memoryFrequency           DisplayString,
              memoryCapacity            DisplayString,
              memoryRank                DisplayString}

                memoryIndex OBJECT-TYPE
                  SYNTAX  INTEGER
                  ACCESS  read-only
                  STATUS  mandatory
                  ::=  { memoryEntry 1 }

                memoryLocation OBJECT-TYPE
                  SYNTAX  DisplayString 
                  ACCESS  read-only
                  STATUS  mandatory
                  ::=  { memoryEntry 2 }

                memoryPresent OBJECT-TYPE
                  SYNTAX  DisplayString
                  ACCESS  read-only
                  STATUS  mandatory
                  ::=  { memoryEntry 3 }
                  
                memoryVendor OBJECT-TYPE
                  SYNTAX  DisplayString
                  ACCESS  read-only
                  STATUS  mandatory
                  ::=  { memoryEntry 4 }
                  
                memoryPN OBJECT-TYPE
                  SYNTAX  DisplayString 
                  ACCESS  read-only
                  STATUS  mandatory
                  ::=  { memoryEntry 5 }

                memorySN OBJECT-TYPE
                  SYNTAX  DisplayString 
                  ACCESS  read-only
                  STATUS  mandatory
                  ::=  { memoryEntry 6 }
                  
                memoryDRAMType OBJECT-TYPE
                  SYNTAX  DisplayString 
                  ACCESS  read-only
                  STATUS  mandatory
                  ::=  { memoryEntry 7 }
                  
                memoryModule OBJECT-TYPE
                  SYNTAX  DisplayString 
                  ACCESS  read-only
                  STATUS  mandatory
                  ::=  { memoryEntry 8 }
                                    
                memoryType OBJECT-TYPE
                  SYNTAX  DisplayString 
                  ACCESS  read-only
                  STATUS  mandatory
                  ::=  { memoryEntry 9 }

                memoryFrequency OBJECT-TYPE
                  SYNTAX  DisplayString 
                  ACCESS  read-only
                  STATUS  mandatory
                  ::=  { memoryEntry 10 }

                memoryCapacity OBJECT-TYPE
                  SYNTAX  DisplayString 
                  ACCESS  read-only
                  STATUS  mandatory
                  ::=  { memoryEntry 11 }
                  
                memoryRank OBJECT-TYPE
                  SYNTAX  DisplayString
                  ACCESS  read-only
                  STATUS  mandatory
                  ::=  { memoryEntry 12 }


         -- HDD Table

        hddTable OBJECT-TYPE
          SYNTAX  SEQUENCE OF HddEntry
          ACCESS  not-accessible
          STATUS  mandatory
          ::= { componentInfo 3 }

            hddEntry OBJECT-TYPE
              SYNTAX  HddEntry
              ACCESS  not-accessible
              STATUS  mandatory
              INDEX   { hddIndex }
              ::= { hddTable 1 }

            HddEntry ::= SEQUENCE {
              hddIndex                  INTEGER,
              hddPresent                DisplayString,
              hddModel                  DisplayString,
              hddMode                   DisplayString,
              hddSN                     DisplayString,
              hddFWVersion              DisplayString,
              hddCapacity               DisplayString,
              hddNvmeBrandName			    DisplayString,
			  hddNvmeVendorID			    DisplayString,
			  hddNvmeMaxLinkSpeed			    DisplayString,
			  hddNvmeMaxLinkWidth			    DisplayString,
			  hddNvmeTemp			    DisplayString,
			  hddNvmeLeftLife			    DisplayString,
			  hddNvmeSMART			    DisplayString
			  }
			                                          

                hddIndex OBJECT-TYPE
                  SYNTAX  INTEGER
                  ACCESS  read-only
                  STATUS  mandatory
                  ::=  { hddEntry 1 }

                hddPresent OBJECT-TYPE
                  SYNTAX  DisplayString
                  ACCESS  read-only
                  STATUS  mandatory
                  ::=  { hddEntry 3 }
                  
                hddModel OBJECT-TYPE
                  SYNTAX  DisplayString
                  ACCESS  read-only
                  STATUS  mandatory
                  ::=  { hddEntry 4 }
                  
                hddMode OBJECT-TYPE
                  SYNTAX  DisplayString
                  ACCESS  read-only
                  STATUS  mandatory
                  ::=  { hddEntry 5 }
                  
                hddSN OBJECT-TYPE
                  SYNTAX  DisplayString
                  ACCESS  read-only
                  STATUS  mandatory
                  ::=  { hddEntry 6 }
                  
                hddFWVersion OBJECT-TYPE
                  SYNTAX  DisplayString
                  ACCESS  read-only
                  STATUS  mandatory
                  ::=  { hddEntry 7 }
                  
                hddCapacity OBJECT-TYPE
                  SYNTAX  DisplayString
                  ACCESS  read-only
                  STATUS  mandatory
                  ::=  { hddEntry 8 }	

                hddNvmeBrandName OBJECT-TYPE
                  SYNTAX  DisplayString
                  ACCESS  read-only
                  STATUS  mandatory
                  ::=  { hddEntry 9 }	
				  
                hddNvmeVendorID OBJECT-TYPE
                  SYNTAX  DisplayString
                  ACCESS  read-only
                  STATUS  mandatory
                  ::=  { hddEntry 10 }		

                hddNvmeMaxLinkSpeed OBJECT-TYPE
                  SYNTAX  DisplayString
                  ACCESS  read-only
                  STATUS  mandatory
                  ::=  { hddEntry 11 }

                hddNvmeMaxLinkWidth OBJECT-TYPE
                  SYNTAX  DisplayString
                  ACCESS  read-only
                  STATUS  mandatory
                  ::=  { hddEntry 12 }

                hddNvmeTemp OBJECT-TYPE
                  SYNTAX  DisplayString
                  ACCESS  read-only
                  STATUS  mandatory
                  ::=  { hddEntry 13 }

                hddNvmeLeftLife OBJECT-TYPE
                  SYNTAX  DisplayString
                  ACCESS  read-only
                  STATUS  mandatory
                  ::=  { hddEntry 14 }

                hddNvmeSMART OBJECT-TYPE
                  SYNTAX  DisplayString
                  ACCESS  read-only
                  STATUS  mandatory
                  ::=  { hddEntry 15 }				  
			
         -- PSU Table

        psuTable OBJECT-TYPE
            SYNTAX  SEQUENCE OF PsuEntry
            ACCESS  not-accessible
            STATUS  mandatory
            ::= { componentInfo 4 }

            psuEntry OBJECT-TYPE
              SYNTAX  PsuEntry
              ACCESS  not-accessible
              STATUS  mandatory
              INDEX   { psuIndex }
              ::= { psuTable 1 }

            PsuEntry ::= SEQUENCE {
              psuIndex                  INTEGER,
              psuLocation               DisplayString,
              psuPresent                DisplayString,
              psuVendor                 DisplayString,
              psuModel                  DisplayString,  
              psuRevision               DisplayString,
              psuDate                   DisplayString,
              psuSN                     DisplayString,  
              psuRatedPower             DisplayString    }

                psuIndex OBJECT-TYPE
                  SYNTAX  INTEGER
                  ACCESS  read-only
                  STATUS  mandatory
                  ::=  { psuEntry 1 }

                psuLocation OBJECT-TYPE
                  SYNTAX  DisplayString 
                  ACCESS  read-only
                  STATUS  mandatory
                  ::=  { psuEntry 2 }
                  
                psuPresent OBJECT-TYPE
                  SYNTAX  DisplayString 
                  ACCESS  read-only
                  STATUS  mandatory
                  ::=  { psuEntry 3 }

                psuVendor OBJECT-TYPE
                  SYNTAX  DisplayString
                  ACCESS  read-only
                  STATUS  mandatory
                  ::=  { psuEntry 4 }
                  
                psuModel OBJECT-TYPE
                  SYNTAX  DisplayString 
                  ACCESS  read-only
                  STATUS  mandatory
                  ::=  { psuEntry 5 }

                psuRevision OBJECT-TYPE
                  SYNTAX  DisplayString
                  ACCESS  read-only
                  STATUS  mandatory
                  ::=  { psuEntry 6 }  
 
                psuDate OBJECT-TYPE
                  SYNTAX  DisplayString
                  ACCESS  read-only
                  STATUS  mandatory
                  ::=  { psuEntry 7 } 
                                   
                psuSN OBJECT-TYPE
                  SYNTAX  DisplayString
                  ACCESS  read-only
                  STATUS  mandatory
                  ::=  { psuEntry 8 }  
                  
                psuRatedPower OBJECT-TYPE
                  SYNTAX  DisplayString
                  ACCESS  read-only
                  STATUS  mandatory
                  ::=  { psuEntry 9 }  

         -- PCIe Table

        pCIeTable OBJECT-TYPE
          SYNTAX  SEQUENCE OF PCIeEntry
          ACCESS  not-accessible
          STATUS  mandatory
          ::= { componentInfo 5 }

            pCIeEntry OBJECT-TYPE
              SYNTAX  PCIeEntry
              ACCESS  not-accessible
              STATUS  mandatory
              INDEX   { pCIeIndex }
              ::= { pCIeTable 1 }

            PCIeEntry ::= SEQUENCE {
              pCIeIndex                  INTEGER,
              pCIeLocation               DisplayString,
              pCIeVendor                 DisplayString,
              pCIeClass                  DisplayString,
              pCIeBrandName              DisplayString,             
              pCIeLinkSpeed              DisplayString,
              pCIeLinkWidth              DisplayString }

                pCIeIndex OBJECT-TYPE
                  SYNTAX  INTEGER
                  ACCESS  read-only
                  STATUS  mandatory
                  ::=  { pCIeEntry 1 }
                  
                pCIeLocation OBJECT-TYPE
                  SYNTAX  DisplayString
                  ACCESS  read-only
                  STATUS  mandatory
                  ::=  { pCIeEntry 2 }

                pCIeVendor OBJECT-TYPE
                  SYNTAX  DisplayString 
                  ACCESS  read-only
                  STATUS  mandatory
                  ::=  { pCIeEntry 3 }

                pCIeClass OBJECT-TYPE
                  SYNTAX  DisplayString
                  ACCESS  read-only
                  STATUS  mandatory
                  ::=  { pCIeEntry 4 }

                pCIeBrandName OBJECT-TYPE
                  SYNTAX  DisplayString
                  ACCESS  read-only
                  STATUS  mandatory
                  ::=  { pCIeEntry 5 }
                                    
                pCIeLinkSpeed OBJECT-TYPE
                  SYNTAX  DisplayString 
                  ACCESS  read-only
                  STATUS  mandatory
                  ::=  { pCIeEntry 6 }

                pCIeLinkWidth OBJECT-TYPE
                  SYNTAX  DisplayString
                  ACCESS  read-only
                  STATUS  mandatory
                  ::=  { pCIeEntry 7 }
                  

         -- nic Table

        nicTable OBJECT-TYPE
          SYNTAX  SEQUENCE OF NicEntry
            ACCESS  not-accessible
            STATUS  mandatory
            ::= { componentInfo 6 }

            nicEntry OBJECT-TYPE
              SYNTAX  NicEntry
              ACCESS  not-accessible
              STATUS  mandatory
              INDEX   { nicIndex }
              ::= { nicTable 1 }

            NicEntry ::= SEQUENCE {
              nicIndex                  INTEGER,
              nicLocation               DisplayString,
			  nicPort                   DisplayString,
			  nicVendor                 DisplayString,
              nicCategory               DisplayString,
			  nicClass                  DisplayString, 
              nicBrandName              DisplayString,                    
              nicLinkSpeed              DisplayString,  
              nicMACGUID            NetworkAddress  }

                nicIndex OBJECT-TYPE
                  SYNTAX  INTEGER
                  ACCESS  read-only
                  STATUS  mandatory
                  ::=  { nicEntry 1 }

                nicLocation OBJECT-TYPE
                  SYNTAX  DisplayString 
                  ACCESS  read-only
                  STATUS  mandatory
                  ::=  { nicEntry 2 }
				  
                  
                nicPort OBJECT-TYPE
                  SYNTAX  DisplayString 
                  ACCESS  read-only
                  STATUS  mandatory
                  ::=  { nicEntry 3 }
				  
				nicVendor OBJECT-TYPE
                  SYNTAX  DisplayString 
                  ACCESS  read-only
                  STATUS  mandatory
                  ::=  { nicEntry 4 }

                nicCategory OBJECT-TYPE
                  SYNTAX  DisplayString
                  ACCESS  read-only
                  STATUS  mandatory
                  ::=  { nicEntry 5 }
                  
                nicClass OBJECT-TYPE
                  SYNTAX  DisplayString
                  ACCESS  read-only
                  STATUS  mandatory
                  ::=  { nicEntry 6 }
                  
                nicBrandName OBJECT-TYPE
                  SYNTAX  DisplayString 
                  ACCESS  read-only
                  STATUS  mandatory
                  ::=  { nicEntry 7 }

                nicLinkSpeed OBJECT-TYPE
                  SYNTAX  DisplayString
                  ACCESS  read-only
                  STATUS  mandatory
                  ::=  { nicEntry 8 }

                nicMACGUID  OBJECT-TYPE
                  SYNTAX  NetworkAddress
                  ACCESS  read-only
                  STATUS  mandatory
                  ::=  { nicEntry 9 }                  
  
--renwh add

        -- RAID Card Table
		
        raidCardTable OBJECT-TYPE
          SYNTAX  SEQUENCE OF RaidCardEntry
          ACCESS  not-accessible
          STATUS  mandatory
          ::= { componentInfo 7 }

            raidCardEntry OBJECT-TYPE
              SYNTAX  RaidCardEntry
              ACCESS  not-accessible
              STATUS  mandatory
              INDEX   { raidCardIndex }
              ::= { raidCardTable 1 }

            RaidCardEntry ::= SEQUENCE {
              raidCardIndex                              INTEGER,
			  raidCardLocation 	                         DisplayString,
			  raidCardPresent                            DisplayString,
			  raidCardAdapterName                        DisplayString,
			  raidCardSerialNum                          DisplayString,
			  raidCardPkgVersion                         DisplayString,
			  raidCardBIOSVersion                        DisplayString,
			  raidCardHIVVersion                         DisplayString,
			  raidCardExpanderVersion                    DisplayString,
			  raidCardNVDATAVersion                      DisplayString,
			  raidCardCPLDVersion                        DisplayString,
			  raidCardPCIVendorID                        DisplayString,
			  raidCardPCIDeviceID                        DisplayString,
			  raidCardPCISubVendorID                     DisplayString,
			  raidCardPCISubSytemID                      DisplayString,
			  raidCardROCTemp                            DisplayString,
			  raidCardExpanderTemp                       DisplayString,
			  raidCardFirmwareBuildTime                  DisplayString,
			  raidCardHostInterface                      DisplayString,
			  raidCardDeviceInterface                    DisplayString,
			  raidCardNvramSize                          DisplayString,
			  raidCardMemorySize                         DisplayString,
			  raidCardFlashSize                          DisplayString,
			  raidCardAutoRebuild                        DisplayString,
			  raidCardSasAddress                         DisplayString,
			  raidCardPortCount                          DisplayString,
			  raidCardPyhsicalDriveCount                 DisplayString,
			  raidCardVitualDriveCount                   DisplayString,
			  raidCardFirmwareVersion                    DisplayString,
			  raidCardMinStripSize                       DisplayString,
			  raidCardSpinDownTime                       DisplayString,
			  raidCardSpinUpDelay                        DisplayString,
			  raidCardCacheFlushInterval                 DisplayString,
			  raidCardRebuildRate                        DisplayString,
			  raidCardResconstructionRate                DisplayString,
			  raidCardCoercionMode                       DisplayString,
			  raidCardBatteryWaring                      DisplayString,
			  raidCardAlarmControl                       DisplayString,
			  raidCardClusterMode                        DisplayString,
			  raidCardControlR                           DisplayString,
			  raidCardMaxStripSize                       DisplayString,
			  raidCardSpinUpDriveCount                   DisplayString,
			  raidCardSmartPolling                       DisplayString,
			  raidCardBackGroundInitRate                 DisplayString,
			  raidCardConsistencyCheckRate               DisplayString,
			  raidCardMaintainFDFailHistory              DisplayString,
			  raidCardSmartCopyBackEnable                DisplayString,
			  raidCardNCQ                                DisplayString,
			  raidCardShieldStateSupported               DisplayString		  
			  }

                raidCardIndex OBJECT-TYPE
                  SYNTAX  INTEGER
                  ACCESS  read-only
                  STATUS  mandatory
                  ::=  { raidCardEntry 1 }

				raidCardLocation OBJECT-TYPE
                  SYNTAX  DisplayString 
                  ACCESS  read-only
                  STATUS  mandatory
                  ::=  { raidCardEntry 2 }

                raidCardPresent OBJECT-TYPE
                  SYNTAX  DisplayString 
                  ACCESS  read-only
                  STATUS  mandatory
                  ::=  { raidCardEntry 3 }

                raidCardAdapterName OBJECT-TYPE
                  SYNTAX  DisplayString
                  ACCESS  read-only
                  STATUS  mandatory
                  ::=  { raidCardEntry 4 }

                raidCardSerialNum OBJECT-TYPE
                  SYNTAX  DisplayString
                  ACCESS  read-only
                  STATUS  mandatory
                  ::=  { raidCardEntry 5 }
				  
                raidCardPkgVersion OBJECT-TYPE
                  SYNTAX  DisplayString
                  ACCESS  read-only
                  STATUS  mandatory
                  ::=  { raidCardEntry 6 }
				  
                raidCardBIOSVersion OBJECT-TYPE
                  SYNTAX  DisplayString
                  ACCESS  read-only
                  STATUS  mandatory
                  ::=  { raidCardEntry 7 }
				  
				raidCardHIVVersion OBJECT-TYPE
                  SYNTAX  DisplayString
                  ACCESS  read-only
                  STATUS  mandatory
                  ::=  { raidCardEntry 8 }
				  
				raidCardExpanderVersion OBJECT-TYPE
                  SYNTAX  DisplayString
                  ACCESS  read-only
                  STATUS  mandatory
                  ::=  { raidCardEntry 9 }
				  
				raidCardNVDATAVersion OBJECT-TYPE
                  SYNTAX  DisplayString
                  ACCESS  read-only
                  STATUS  mandatory
                  ::=  { raidCardEntry 10 }
				  
				raidCardCPLDVersion OBJECT-TYPE
                  SYNTAX  DisplayString
                  ACCESS  read-only
                  STATUS  mandatory
                  ::=  { raidCardEntry 11 }
				  
				raidCardPCIVendorID OBJECT-TYPE
                  SYNTAX  DisplayString
                  ACCESS  read-only
                  STATUS  mandatory
                  ::=  { raidCardEntry 12 }
				  
				raidCardPCIDeviceID OBJECT-TYPE
                  SYNTAX  DisplayString
                  ACCESS  read-only
                  STATUS  mandatory
                  ::=  { raidCardEntry 13 }
				  
				raidCardPCISubVendorID OBJECT-TYPE
                  SYNTAX  DisplayString
                  ACCESS  read-only
                  STATUS  mandatory
                  ::=  { raidCardEntry 14 }
				  
				raidCardPCISubSytemID OBJECT-TYPE
                  SYNTAX  DisplayString
                  ACCESS  read-only
                  STATUS  mandatory
                  ::=  { raidCardEntry 15 }
				  
				
				  
				raidCardROCTemp OBJECT-TYPE
                  SYNTAX  DisplayString
                  ACCESS  read-only
                  STATUS  mandatory
                  ::=  { raidCardEntry 17 }
				  
				raidCardExpanderTemp OBJECT-TYPE
                  SYNTAX  DisplayString
                  ACCESS  read-only
                  STATUS  mandatory
                  ::=  { raidCardEntry 18 }
 
  				raidCardFirmwareBuildTime OBJECT-TYPE
                  SYNTAX  DisplayString
                  ACCESS  read-only
                  STATUS  mandatory
                  ::=  { raidCardEntry 20 }
				  
			    raidCardHostInterface OBJECT-TYPE
                  SYNTAX  DisplayString
                  ACCESS  read-only
                  STATUS  mandatory
                  ::=  { raidCardEntry 21 }
			  
			    raidCardDeviceInterface  OBJECT-TYPE
                  SYNTAX  DisplayString
                  ACCESS  read-only
                  STATUS  mandatory
                  ::=  { raidCardEntry 22 }
			  
			    raidCardNvramSize  OBJECT-TYPE
                  SYNTAX  DisplayString
                  ACCESS  read-only
                  STATUS  mandatory
                  ::=  { raidCardEntry 23 }
			  
			    raidCardMemorySize  OBJECT-TYPE
                  SYNTAX  DisplayString
                  ACCESS  read-only
                  STATUS  mandatory
                  ::=  { raidCardEntry 24 }
			  
			    raidCardFlashSize  OBJECT-TYPE
                  SYNTAX  DisplayString
                  ACCESS  read-only
                  STATUS  mandatory
                  ::=  { raidCardEntry 25 }
			  
			    raidCardAutoRebuild  OBJECT-TYPE
                  SYNTAX  DisplayString
                  ACCESS  read-only
                  STATUS  mandatory
                  ::=  { raidCardEntry 26 }
			  
			    raidCardSasAddress  OBJECT-TYPE
                  SYNTAX  DisplayString
                  ACCESS  read-only
                  STATUS  mandatory
                  ::=  { raidCardEntry 27 }
			  
			    raidCardPortCount  OBJECT-TYPE
                  SYNTAX  DisplayString
                  ACCESS  read-only
                  STATUS  mandatory
                  ::=  { raidCardEntry 28 }
			  
			    raidCardPyhsicalDriveCount  OBJECT-TYPE
                  SYNTAX  DisplayString
                  ACCESS  read-only
                  STATUS  mandatory
                  ::=  { raidCardEntry 29 }
			  
			    raidCardVitualDriveCount  OBJECT-TYPE
                  SYNTAX  DisplayString
                  ACCESS  read-only
                  STATUS  mandatory
                  ::=  { raidCardEntry 30 }
			  
			    raidCardFirmwareVersion  OBJECT-TYPE
                  SYNTAX  DisplayString
                  ACCESS  read-only
                  STATUS  mandatory
                  ::=  { raidCardEntry 31 }
			  
			    raidCardMinStripSize  OBJECT-TYPE
                  SYNTAX  DisplayString
                  ACCESS  read-only
                  STATUS  mandatory
                  ::=  { raidCardEntry 32 }
			  
			    raidCardSpinDownTime  OBJECT-TYPE
                  SYNTAX  DisplayString
                  ACCESS  read-only
                  STATUS  mandatory
                  ::=  { raidCardEntry 33 }
			  
			    raidCardSpinUpDelay  OBJECT-TYPE
                  SYNTAX  DisplayString
                  ACCESS  read-only
                  STATUS  mandatory
                  ::=  { raidCardEntry 34 }
			  
			    raidCardCacheFlushInterval  OBJECT-TYPE
                  SYNTAX  DisplayString
                  ACCESS  read-only
                  STATUS  mandatory
                  ::=  { raidCardEntry 35 }
			  
			    raidCardRebuildRate  OBJECT-TYPE
                  SYNTAX  DisplayString
                  ACCESS  read-only
                  STATUS  mandatory
                  ::=  { raidCardEntry 36 }
			  
			    raidCardResconstructionRate  OBJECT-TYPE
                  SYNTAX  DisplayString
                  ACCESS  read-only
                  STATUS  mandatory
                  ::=  { raidCardEntry 37 }
			  
			    raidCardCoercionMode  OBJECT-TYPE
                  SYNTAX  DisplayString
                  ACCESS  read-only
                  STATUS  mandatory
                  ::=  { raidCardEntry 38 }
			  
			    raidCardBatteryWaring  OBJECT-TYPE
                  SYNTAX  DisplayString
                  ACCESS  read-only
                  STATUS  mandatory
                  ::=  { raidCardEntry 39 }
			  
			    raidCardAlarmControl  OBJECT-TYPE
                  SYNTAX  DisplayString
                  ACCESS  read-only
                  STATUS  mandatory
                  ::=  { raidCardEntry 40 }
			  
			    raidCardClusterMode  OBJECT-TYPE
                  SYNTAX  DisplayString
                  ACCESS  read-only
                  STATUS  mandatory
                  ::=  { raidCardEntry 41 }
			  
			    raidCardControlR  OBJECT-TYPE
                  SYNTAX  DisplayString
                  ACCESS  read-only
                  STATUS  mandatory
                  ::=  { raidCardEntry 42 }
			  
			    raidCardMaxStripSize  OBJECT-TYPE
                  SYNTAX  DisplayString
                  ACCESS  read-only
                  STATUS  mandatory
                  ::=  { raidCardEntry 43 }
			  
			    raidCardSpinUpDriveCount   OBJECT-TYPE
                  SYNTAX  DisplayString
                  ACCESS  read-only
                  STATUS  mandatory
                  ::=  { raidCardEntry 44 }
				raidCardSmartPolling   OBJECT-TYPE
                  SYNTAX  DisplayString
                  ACCESS  read-only
                  STATUS  mandatory
                  ::=  { raidCardEntry 45 }
				raidCardBackGroundInitRate   OBJECT-TYPE
                  SYNTAX  DisplayString
                  ACCESS  read-only
                  STATUS  mandatory
                  ::=  { raidCardEntry 46 }
				raidCardConsistencyCheckRate   OBJECT-TYPE
                  SYNTAX  DisplayString
                  ACCESS  read-only
                  STATUS  mandatory
                  ::=  { raidCardEntry 47 }
				raidCardMaintainFDFailHistory   OBJECT-TYPE
                  SYNTAX  DisplayString
                  ACCESS  read-only
                  STATUS  mandatory
                  ::=  { raidCardEntry 48 }
				raidCardSmartCopyBackEnable   OBJECT-TYPE
                  SYNTAX  DisplayString
                  ACCESS  read-only
                  STATUS  mandatory
                  ::=  { raidCardEntry 49 }
				raidCardNCQ   OBJECT-TYPE
                  SYNTAX  DisplayString
                  ACCESS  read-only
                  STATUS  mandatory
                  ::=  { raidCardEntry 50 }
				raidCardShieldStateSupported   OBJECT-TYPE
                  SYNTAX  DisplayString
                  ACCESS  read-only
                  STATUS  mandatory
                  ::=  { raidCardEntry 51 }
				  
			  
			  
	-- hddUnderCard Table
	hddUnderRaidCardTable OBJECT-TYPE
	  SYNTAX  SEQUENCE OF HddUnderRaidCardEntry
	  ACCESS  not-accessible
	  STATUS  mandatory
	  ::= { componentInfo 8 }
	  
		hddUnderRaidCardEntry OBJECT-TYPE
		  SYNTAX  HddUnderRaidCardEntry
		  ACCESS  not-accessible
		  STATUS  mandatory
		  INDEX   { hddInRaidIndex }
		  ::= { hddUnderRaidCardTable 1 }

		HddUnderRaidCardEntry ::= SEQUENCE {
		  hddInRaidIndex     INTEGER,
		  hddInRaidPresent   DisplayString,
		  hddInRaidCtrlID    DisplayString,
		  hddInRaidDevID	DisplayString,
		  hddInRaidType		DisplayString,
		  hddInRaidState		DisplayString,
		  hddInRaidVendorID		DisplayString,
		  hddInRaidProductID		DisplayString,
		  hddInRaidSlot		DisplayString,
		  hddInRaidPresent2           DisplayString,
		  hddInRaidInterfaceType	DisplayString,
		  hddInRaidSpeed		DisplayString,
		  hddInRaidSize64		DisplayString,
		  hddInRaidLinkSpeed		DisplayString,
		  hddInRaidPowerState		DisplayString,
		  hddInRaidTemperature	DisplayString,
		  hddInRaidLifeSpan 		  DisplayString,
		  hddInRaidRotationSpeed	DisplayString,
      		  hddInRaidJbodType	      	DisplayString
		  }

			hddInRaidIndex OBJECT-TYPE
			  SYNTAX  INTEGER
			  ACCESS  read-only
			  STATUS  mandatory
			  ::=  { hddUnderRaidCardEntry 1 }

			hddInRaidPresent OBJECT-TYPE
			  SYNTAX  DisplayString 
			  ACCESS  read-only
			  STATUS  mandatory
			  ::=  { hddUnderRaidCardEntry 2 }
			  
			hddInRaidCtrlID OBJECT-TYPE
			  SYNTAX  DisplayString 
			  ACCESS  read-only
			  STATUS  mandatory
			  ::=  { hddUnderRaidCardEntry 3 }				 
	  
			hddInRaidDevID OBJECT-TYPE
			  SYNTAX  DisplayString 
			  ACCESS  read-only
			  STATUS  mandatory
			  ::=  { hddUnderRaidCardEntry 4 }
	  
			hddInRaidType OBJECT-TYPE
			  SYNTAX  DisplayString 
			  ACCESS  read-only
			  STATUS  mandatory
			  ::=  { hddUnderRaidCardEntry 5 }

			hddInRaidState OBJECT-TYPE
			  SYNTAX  DisplayString 
			  ACCESS  read-only
			  STATUS  mandatory
			  ::=  { hddUnderRaidCardEntry 6 }

			hddInRaidVendorID OBJECT-TYPE
			  SYNTAX  DisplayString 
			  ACCESS  read-only
			  STATUS  mandatory
			  ::=  { hddUnderRaidCardEntry 7 }

			hddInRaidProductID OBJECT-TYPE
			  SYNTAX  DisplayString 
			  ACCESS  read-only
			  STATUS  mandatory
			  ::=  { hddUnderRaidCardEntry 8 }
						  	  				  
			hddInRaidSlot OBJECT-TYPE
			  SYNTAX  DisplayString 
			  ACCESS  read-only
			  STATUS  mandatory
			  ::=  { hddUnderRaidCardEntry 11 }	

			hddInRaidPresent2 OBJECT-TYPE
			  SYNTAX  DisplayString 
			  ACCESS  read-only
			  STATUS  mandatory
			  ::=  { hddUnderRaidCardEntry 12 }
			  						  
			  
			hddInRaidInterfaceType OBJECT-TYPE
			  SYNTAX  DisplayString 
			  ACCESS  read-only
			  STATUS  mandatory
			  ::=  { hddUnderRaidCardEntry 14 }						  
		  						  
			  						  
			hddInRaidSpeed OBJECT-TYPE
			  SYNTAX  DisplayString 
			  ACCESS  read-only
			  STATUS  mandatory
			  ::=  { hddUnderRaidCardEntry 16 }						  
			  
			hddInRaidSize64 OBJECT-TYPE
			  SYNTAX  DisplayString 
			  ACCESS  read-only
			  STATUS  mandatory
			  ::=  { hddUnderRaidCardEntry 17 }						  
			    
			hddInRaidLinkSpeed OBJECT-TYPE
			  SYNTAX  DisplayString 
			  ACCESS  read-only
			  STATUS  mandatory
			  ::=  { hddUnderRaidCardEntry 19 }
			  
			hddInRaidPowerState OBJECT-TYPE
			  SYNTAX  DisplayString 
			  ACCESS  read-only
			  STATUS  mandatory
			  ::=  { hddUnderRaidCardEntry 20 }						  
			  
			hddInRaidTemperature OBJECT-TYPE
			  SYNTAX  DisplayString 
			  ACCESS  read-only
			  STATUS  mandatory
			  ::=  { hddUnderRaidCardEntry 21 }

			hddInRaidLifeSpan OBJECT-TYPE
			  SYNTAX  DisplayString 
			  ACCESS  read-only
			  STATUS  mandatory
			  ::=  { hddUnderRaidCardEntry 25 }
			  
			hddInRaidRotationSpeed OBJECT-TYPE
			  SYNTAX  DisplayString 
			  ACCESS  read-only
			  STATUS  mandatory
			  ::=  { hddUnderRaidCardEntry 26 }
      
      			hddInRaidJbodType OBJECT-TYPE
			  SYNTAX  DisplayString 
			  ACCESS  read-only
			  STATUS  mandatory
			  ::=  { hddUnderRaidCardEntry 27 }
			  				  					  					  
						
	-- logRaidUnderRaidCard Table
	logicDevUnderRaidCardTable OBJECT-TYPE
	  SYNTAX  SEQUENCE OF LogicDevUnderRaidCardEntry
	  ACCESS  not-accessible
	  STATUS  mandatory
	  ::= { componentInfo 9 }
	  
		logicDevUnderRaidCardEntry OBJECT-TYPE
		  SYNTAX  LogicDevUnderRaidCardEntry
		  ACCESS  not-accessible
		  STATUS  mandatory
		  INDEX   { logicDevIndex }
		  ::= { logicDevUnderRaidCardTable 1 }

		LogicDevUnderRaidCardEntry ::= SEQUENCE {
		  logicDevIndex    	 INTEGER,
		  logicCtrlID			DisplayString,
		  logicDevID			DisplayString,
		  logicDevLDName		DisplayString,
		  logicDevType			DisplayString,
		  logicDevState			DisplayString,
		  logicDevStripeSize		DisplayString,
		  logicDevAccessPolicy	DisplayString,
		  logicDevReadPolicy		DisplayString,
		  logicDevWritePolicy	DisplayString,
		  logicDevCachePolicy	DisplayString,
		  logicDevBGI			DisplayString,
		  logicDevSSDCaching	DisplayString,
		  logicDevSize			DisplayString
		   }

			logicDevIndex OBJECT-TYPE
			  SYNTAX  INTEGER
			  ACCESS  read-only
			  STATUS  mandatory
			  ::=  { logicDevUnderRaidCardEntry 1 }
			  
			  
			logicCtrlID OBJECT-TYPE
			  SYNTAX  DisplayString 
			  ACCESS  read-only
			  STATUS  mandatory
			  ::=  { logicDevUnderRaidCardEntry 2 }	

			  
			logicDevID OBJECT-TYPE
			  SYNTAX  DisplayString 
			  ACCESS  read-only
			  STATUS  mandatory
			  ::=  { logicDevUnderRaidCardEntry 3 }						  
		 
			logicDevLDName OBJECT-TYPE
			  SYNTAX  DisplayString 
			  ACCESS  read-only
			  STATUS  mandatory
			  ::=  { logicDevUnderRaidCardEntry 4 }

			logicDevType OBJECT-TYPE
			  SYNTAX  DisplayString 
			  ACCESS  read-only
			  STATUS  mandatory
			  ::=  { logicDevUnderRaidCardEntry 5 }

			logicDevState OBJECT-TYPE
			  SYNTAX  DisplayString 
			  ACCESS  read-only
			  STATUS  mandatory
			  ::=  { logicDevUnderRaidCardEntry 6 }

			logicDevStripeSize OBJECT-TYPE
			  SYNTAX  DisplayString 
			  ACCESS  read-only
			  STATUS  mandatory
			  ::=  { logicDevUnderRaidCardEntry 7 }

			logicDevAccessPolicy OBJECT-TYPE
			  SYNTAX  DisplayString 
			  ACCESS  read-only
			  STATUS  mandatory
			  ::=  { logicDevUnderRaidCardEntry 8 }

			logicDevReadPolicy OBJECT-TYPE
			  SYNTAX  DisplayString 
			  ACCESS  read-only
			  STATUS  mandatory
			  ::=  { logicDevUnderRaidCardEntry 9 }

			logicDevWritePolicy OBJECT-TYPE
			  SYNTAX  DisplayString 
			  ACCESS  read-only
			  STATUS  mandatory
			  ::=  { logicDevUnderRaidCardEntry 10 }

			logicDevCachePolicy OBJECT-TYPE
			  SYNTAX  DisplayString 
			  ACCESS  read-only
			  STATUS  mandatory
			  ::=  { logicDevUnderRaidCardEntry 11 }

			logicDevBGI OBJECT-TYPE
			  SYNTAX  DisplayString 
			  ACCESS  read-only
			  STATUS  mandatory
			  ::=  { logicDevUnderRaidCardEntry 12 }

			logicDevSSDCaching OBJECT-TYPE
			  SYNTAX  DisplayString 
			  ACCESS  read-only
			  STATUS  mandatory
			  ::=  { logicDevUnderRaidCardEntry 13 }

			logicDevSize OBJECT-TYPE
			  SYNTAX  DisplayString 
			  ACCESS  read-only
			  STATUS  mandatory
			  ::=  { logicDevUnderRaidCardEntry 16 }
						
						  
  --sasit

        -- SASIT Card Table
    
        sASITCardTable OBJECT-TYPE
          SYNTAX  SEQUENCE OF SASITCardEntry
          ACCESS  not-accessible
          STATUS  mandatory
          ::= { componentInfo 10 }

            sASITCardEntry OBJECT-TYPE
              SYNTAX  SASITCardEntry
              ACCESS  not-accessible
              STATUS  mandatory
              INDEX   { sASITCardIndex }
              ::= { sASITCardTable 1 }

            SASITCardEntry ::= SEQUENCE {
              sASITCardIndex                  INTEGER,
              sASITCardLocation               DisplayString,
              sASITCardPresent                DisplayString,
              sASITCardBoardName              DisplayString,
              sASITCardSASAddress             DisplayString,
              sASITCardFWVersion              DisplayString,
              sASITCardNVDATAVersion          DisplayString,
              sASITCardPCIVensorID            DisplayString,
              sASITCardPCIDeviceID            DisplayString,
              sASITCardPCISubvendorID         DisplayString,
              sASITCardPCISubsystemID         DisplayString,
              sASITCardSpeed                  DisplayString,
              sASITCardIOCTemp                DisplayString }

                sASITCardIndex OBJECT-TYPE
                  SYNTAX  INTEGER
                  ACCESS  read-only
                  STATUS  mandatory
                  ::=  { sASITCardEntry 1 }

                sASITCardLocation OBJECT-TYPE
                  SYNTAX  DisplayString 
                  ACCESS  read-only
                  STATUS  mandatory
                  ::=  { sASITCardEntry 2 }

                sASITCardPresent OBJECT-TYPE
                  SYNTAX  DisplayString
                  ACCESS  read-only
                  STATUS  mandatory
                  ::=  { sASITCardEntry 3 }

                sASITCardBoardName OBJECT-TYPE
                  SYNTAX  DisplayString
                  ACCESS  read-only
                  STATUS  mandatory
                  ::=  { sASITCardEntry 4 }
          
                sASITCardSASAddress OBJECT-TYPE
                  SYNTAX  DisplayString
                  ACCESS  read-only
                  STATUS  mandatory
                  ::=  { sASITCardEntry 5 }
          
                sASITCardFWVersion OBJECT-TYPE
                  SYNTAX  DisplayString
                  ACCESS  read-only
                  STATUS  mandatory
                  ::=  { sASITCardEntry 6 }
          
                sASITCardNVDATAVersion OBJECT-TYPE
                  SYNTAX  DisplayString
                  ACCESS  read-only
                  STATUS  mandatory
                  ::=  { sASITCardEntry 7 }
          
                sASITCardPCIVensorID OBJECT-TYPE
                  SYNTAX  DisplayString
                  ACCESS  read-only
                  STATUS  mandatory
                  ::=  { sASITCardEntry 8 }
          
                sASITCardPCIDeviceID OBJECT-TYPE
                  SYNTAX  DisplayString
                  ACCESS  read-only
                  STATUS  mandatory
                  ::=  { sASITCardEntry 9 }
          
                sASITCardPCISubvendorID OBJECT-TYPE
                  SYNTAX  DisplayString
                  ACCESS  read-only
                  STATUS  mandatory
                  ::=  { sASITCardEntry 10 }
          
                sASITCardPCISubsystemID OBJECT-TYPE
                  SYNTAX  DisplayString
                  ACCESS  read-only
                  STATUS  mandatory
                  ::=  { sASITCardEntry 11 }
          
                sASITCardSpeed OBJECT-TYPE
                  SYNTAX  DisplayString
                  ACCESS  read-only
                  STATUS  mandatory
                  ::=  { sASITCardEntry 12 }
          
                sASITCardIOCTemp OBJECT-TYPE
                  SYNTAX  DisplayString
                  ACCESS  read-only
                  STATUS  mandatory
                  ::=  { sASITCardEntry 13 }
          
    -- hddUnderThisCard Table
    hddUnderSASITCardTable OBJECT-TYPE
      SYNTAX  SEQUENCE OF HddUnderSASITCardEntry
      ACCESS  not-accessible
      STATUS  mandatory
      ::= { componentInfo 11 }
      
      hddUnderSASITCardEntry OBJECT-TYPE
        SYNTAX  HddUnderSASITCardEntry
        ACCESS  not-accessible
        STATUS  mandatory
        INDEX   { hddUnderSASITCardIndex }
        ::= { hddUnderSASITCardTable 1 }

      HddUnderSASITCardEntry ::= SEQUENCE {
        hddUnderSASITCardIndex                  INTEGER,
        hddUnderSASITCardPresent                DisplayString,
        hddUnderSASITCardCtrlID                 DisplayString,
        hddUnderSASITCardDevID                  DisplayString,
        hddUnderSASITCardType                   DisplayString,
        hddUnderSASITCardState                  DisplayString,
        hddUnderSASITCardVendorID               DisplayString,
        hddUnderSASITCardProductID              DisplayString,
        hddUnderSASITCardSerialNum              DisplayString,
        hddUnderSASITCardRevisionLevel         DisplayString,
        hddUnderSASITCardSlot                   DisplayString,
        hddUnderSASITCardLEDStatus              DisplayString,
        hddUnderSASITCardInterfaceType          DisplayString,
        hddUnderSASITCardsize64                 DisplayString,
        hddUnderSASITCardSpeed                  DisplayString,
        hddUnderSASITCardPowerState             DisplayString,
        hddUnderSASITCardTemperature            DisplayString,
        hddUnderSASITCardSmart                  DisplayString,
        hddUnderSASITCardLifeSpan               DisplayString,
        hddUnderSASITCardRotationSpeed          DisplayString
      }

        hddUnderSASITCardIndex OBJECT-TYPE
          SYNTAX  INTEGER
          ACCESS  read-only
          STATUS  mandatory
          ::=  { hddUnderSASITCardEntry 1 }

        hddUnderSASITCardPresent OBJECT-TYPE
          SYNTAX  DisplayString 
          ACCESS  read-only
          STATUS  mandatory
          ::=  { hddUnderSASITCardEntry 2 }
          
        hddUnderSASITCardCtrlID OBJECT-TYPE
          SYNTAX  DisplayString 
          ACCESS  read-only
          STATUS  mandatory
          ::=  { hddUnderSASITCardEntry 3 }            
      
        hddUnderSASITCardDevID OBJECT-TYPE
          SYNTAX  DisplayString 
          ACCESS  read-only
          STATUS  mandatory
          ::=  { hddUnderSASITCardEntry 4 }
      
        hddUnderSASITCardType OBJECT-TYPE
          SYNTAX  DisplayString 
          ACCESS  read-only
          STATUS  mandatory
          ::=  { hddUnderSASITCardEntry 5 }

        hddUnderSASITCardState OBJECT-TYPE
          SYNTAX  DisplayString 
          ACCESS  read-only
          STATUS  mandatory
          ::=  { hddUnderSASITCardEntry 6 }

        hddUnderSASITCardVendorID OBJECT-TYPE
          SYNTAX  DisplayString 
          ACCESS  read-only
          STATUS  mandatory
          ::=  { hddUnderSASITCardEntry 7 }

        hddUnderSASITCardProductID OBJECT-TYPE
          SYNTAX  DisplayString 
          ACCESS  read-only
          STATUS  mandatory
          ::=  { hddUnderSASITCardEntry 8 }
          
        hddUnderSASITCardSerialNum OBJECT-TYPE
          SYNTAX  DisplayString 
          ACCESS  read-only
          STATUS  mandatory
          ::=  { hddUnderSASITCardEntry 9 }             
          
        hddUnderSASITCardRevisionLevel OBJECT-TYPE
          SYNTAX  DisplayString 
          ACCESS  read-only
          STATUS  mandatory
          ::=  { hddUnderSASITCardEntry 10 }              
          
        hddUnderSASITCardSlot OBJECT-TYPE
          SYNTAX  DisplayString 
          ACCESS  read-only
          STATUS  mandatory
          ::=  { hddUnderSASITCardEntry 11 }              
          
        hddUnderSASITCardLEDStatus OBJECT-TYPE
          SYNTAX  DisplayString 
          ACCESS  read-only
          STATUS  mandatory
          ::=  { hddUnderSASITCardEntry 12 }              
          
        hddUnderSASITCardInterfaceType OBJECT-TYPE
          SYNTAX  DisplayString 
          ACCESS  read-only
          STATUS  mandatory
          ::=  { hddUnderSASITCardEntry 13 }              
                        
        hddUnderSASITCardsize64 OBJECT-TYPE
          SYNTAX  DisplayString 
          ACCESS  read-only
          STATUS  mandatory
          ::=  { hddUnderSASITCardEntry 14 }              
          
        hddUnderSASITCardSpeed OBJECT-TYPE
          SYNTAX  DisplayString 
          ACCESS  read-only
          STATUS  mandatory
          ::=  { hddUnderSASITCardEntry 15 }              
          
        hddUnderSASITCardPowerState OBJECT-TYPE
          SYNTAX  DisplayString 
          ACCESS  read-only
          STATUS  mandatory
          ::=  { hddUnderSASITCardEntry 16 }              
          
        hddUnderSASITCardTemperature OBJECT-TYPE
          SYNTAX  DisplayString 
          ACCESS  read-only
          STATUS  mandatory
          ::=  { hddUnderSASITCardEntry 17 }              
          
        hddUnderSASITCardSmart OBJECT-TYPE
          SYNTAX  DisplayString 
          ACCESS  read-only
          STATUS  mandatory
          ::=  { hddUnderSASITCardEntry 18 }
          
        hddUnderSASITCardLifeSpan OBJECT-TYPE
          SYNTAX  DisplayString 
          ACCESS  read-only
          STATUS  mandatory
          ::=  { hddUnderSASITCardEntry 19 }              
          
        hddUnderSASITCardRotationSpeed OBJECT-TYPE
          SYNTAX  DisplayString 
          ACCESS  read-only
          STATUS  mandatory
          ::=  { hddUnderSASITCardEntry 20 }              
              
              
-- Fan Table
		
        fanTable OBJECT-TYPE
          SYNTAX  SEQUENCE OF FanEntry
          ACCESS  not-accessible
          STATUS  mandatory
          ::= { componentInfo 12 }

            fanEntry OBJECT-TYPE
              SYNTAX  FanEntry
              ACCESS  not-accessible
              STATUS  mandatory
              INDEX   { fanIndex }
              ::= { fanTable 1 }

            FanEntry ::= SEQUENCE {
              fanIndex                  INTEGER,
              fanLocation               DisplayString,
              fanCoolingPolicy          DisplayString,
              fanCurrentTachSpeed       DisplayString}
              
                fanIndex OBJECT-TYPE
                  SYNTAX  INTEGER
                  ACCESS  read-only
                  STATUS  mandatory
                  ::=  { fanEntry 1 }

                fanLocation OBJECT-TYPE
                  SYNTAX  DisplayString 
                  ACCESS  read-only
                  STATUS  mandatory
                  ::=  { fanEntry 2 }

                fanCoolingPolicy OBJECT-TYPE
                  SYNTAX  DisplayString
                  ACCESS  read-only
                  STATUS  mandatory
                  ::=  { fanEntry 3 }

                fanCurrentTachSpeed OBJECT-TYPE
                  SYNTAX  DisplayString
                  ACCESS  read-only
                  STATUS  mandatory
                  ::=  { fanEntry 4 }
                  
--renwh add end

  
          
--  ************************biosInfo**********************     
     
    biosInfo OBJECT IDENTIFIER     ::=  { bmc 5 }
    
        biosFwVersion OBJECT-TYPE
          SYNTAX  DisplayString 
          ACCESS  read-only
          STATUS  mandatory
          DESCRIPTION "BIOS firmware Version"
          ::=  { biosInfo 1 }
          
        meVersion OBJECT-TYPE
          SYNTAX  DisplayString 
          ACCESS  read-only
          STATUS  mandatory
          DESCRIPTION "ME Version"
          ::=  { biosInfo 2 }
          
          
--  ************************fru**********************     
     
    fru OBJECT IDENTIFIER     ::=  { bmc 7 }
    
        chassis OBJECT IDENTIFIER     ::=  { fru 1 }
    
            chassisType OBJECT-TYPE
              SYNTAX  DisplayString 
              ACCESS  read-only
              STATUS  mandatory
              ::=  { chassis 1 }
          
            chassisPN OBJECT-TYPE
              SYNTAX  DisplayString 
              ACCESS  read-only
              STATUS  mandatory
              ::=  { chassis 2 }
              
            chassisSN OBJECT-TYPE
              SYNTAX  DisplayString 
              ACCESS  read-only
              STATUS  mandatory
              ::=  { chassis 3 }
              
        board OBJECT IDENTIFIER     ::=  { fru 2 }
    
            boardManufacturer OBJECT-TYPE
              SYNTAX  DisplayString 
              ACCESS  read-only
              STATUS  mandatory
              ::=  { board 1 }
          
            boardProductName OBJECT-TYPE
              SYNTAX  DisplayString 
              ACCESS  read-only
              STATUS  mandatory
              ::=  { board 2 }
              
            boardSN OBJECT-TYPE
              SYNTAX  DisplayString 
              ACCESS  read-only
              STATUS  mandatory
              ::=  { board 3 }
              
            boardPN OBJECT-TYPE
              SYNTAX  DisplayString 
              ACCESS  read-only
              STATUS  mandatory
              ::=  { board 4 }
              
        product OBJECT IDENTIFIER     ::=  { fru 3 }
    
            productManufacturer OBJECT-TYPE
              SYNTAX  DisplayString 
              ACCESS  read-only
              STATUS  mandatory
              ::=  { product 1 }
          
            productName OBJECT-TYPE
              SYNTAX  DisplayString 
              ACCESS  read-only
              STATUS  mandatory
              ::=  { product 2 }
              
            productPN OBJECT-TYPE
              SYNTAX  DisplayString 
              ACCESS  read-only
              STATUS  mandatory
              ::=  { product 3 }
              
            productVersion OBJECT-TYPE
              SYNTAX  DisplayString 
              ACCESS  read-only
              STATUS  mandatory
              ::=  { product 4 }
              
            productSN OBJECT-TYPE
              SYNTAX  DisplayString 
              ACCESS  read-only
              STATUS  mandatory
              ::=  { product 5 }
	      
            productAssetTag OBJECT-TYPE
              SYNTAX  DisplayString 
              ACCESS  read-only
              STATUS  mandatory
              ::=  { product 6 }
 
 

--  ************************serverHealth**********************     
     
    serverHealth OBJECT IDENTIFIER                ::=  { bmc 11 }  
    
		    systemHealthStatus OBJECT-TYPE   
			    SYNTAX DisplayString
			    ACCESS read-only
			    STATUS current
			    DESCRIPTION
			    "
			    "
			    ::= { serverHealth 1 }     

		    mBHealthStatus OBJECT-TYPE   
			    SYNTAX DisplayString
			    ACCESS read-only
			    STATUS current
			    DESCRIPTION
			    "
			    "
			    ::= { serverHealth 2 }   

    cpuHealth OBJECT IDENTIFIER                ::=  { serverHealth 3 }
    
		    cpuHealthAllStatus OBJECT-TYPE   
			    SYNTAX DisplayString
			    ACCESS read-only
			    STATUS current
			    DESCRIPTION
			    "
			    "
			    ::= { cpuHealth 1 }  
			     
        cpuHealthTable OBJECT-TYPE
          SYNTAX  SEQUENCE OF CpuHealthEntry
          ACCESS  not-accessible
          STATUS  mandatory
          ::= { cpuHealth 2 }

            cpuHealthEntry OBJECT-TYPE
              SYNTAX  CpuHealthEntry
              ACCESS  not-accessible
              STATUS  mandatory
              INDEX   { cpuHealthIndex }
              ::= { cpuHealthTable 1 }

            CpuHealthEntry ::= SEQUENCE {
              cpuHealthIndex                      INTEGER,
              cpuHealthLocation                   DisplayString,
              cpuHealthStateLevel                 DisplayString, 
              cpuHealthTemp                       DisplayString,
              cpuHealthState                      DisplayString  } 

		            cpuHealthIndex OBJECT-TYPE   
			            SYNTAX INTEGER
			            ACCESS read-only
			            STATUS current
			            DESCRIPTION
			            "
			            "
			            ::= { cpuHealthEntry 1 } 

		            cpuHealthLocation OBJECT-TYPE   
			            SYNTAX DisplayString
			            ACCESS read-only
			            STATUS current
			            DESCRIPTION
			            "
			            "
			            ::= { cpuHealthEntry 2 } 

		            cpuHealthStateLevel OBJECT-TYPE   
			            SYNTAX DisplayString
			            ACCESS read-only
			            STATUS current
			            DESCRIPTION
			            "
			            "
			            ::= { cpuHealthEntry 3 } 
   
		            cpuHealthTemp OBJECT-TYPE   
			            SYNTAX DisplayString
			            ACCESS read-only
			            STATUS current
			            DESCRIPTION
			            "
			            "
			            ::= { cpuHealthEntry 4 } 			            

		            cpuHealthState OBJECT-TYPE   
			            SYNTAX DisplayString
			            ACCESS read-only
			            STATUS current
			            DESCRIPTION
			            "
			            "
			            ::= { cpuHealthEntry 5 } 				            

    memHealth OBJECT IDENTIFIER                ::=  { serverHealth 4 }
    	
		    memHealthAllStatus OBJECT-TYPE   
			    SYNTAX DisplayString
			    ACCESS read-only
			    STATUS current
			    DESCRIPTION
			    "
			    "
			    ::= { memHealth 1 }  
			     
        memHealthTable OBJECT-TYPE
          SYNTAX  SEQUENCE OF MemHealthEntry
          ACCESS  not-accessible
          STATUS  mandatory
          ::= { memHealth 2 }

            memHealthEntry OBJECT-TYPE
              SYNTAX  MemHealthEntry
              ACCESS  not-accessible
              STATUS  mandatory
              INDEX   { memHealthIndex }
              ::= { memHealthTable 1 }

            MemHealthEntry ::= SEQUENCE {
              memHealthIndex                      INTEGER,
              memHealthLocation                   DisplayString,
              memHealthStateLevel                 DisplayString,
              memHealthTemp                       DisplayString,
              memHealthWorkFrequency              DisplayString,
              memHealthState                      DisplayString  } 

		            memHealthIndex OBJECT-TYPE   
			            SYNTAX INTEGER
			            ACCESS read-only
			            STATUS current
			            DESCRIPTION
			            "Memory Index"
			            ::= { memHealthEntry 1 } 

		            memHealthLocation OBJECT-TYPE   
			            SYNTAX DisplayString
			            ACCESS read-only
			            STATUS current
			            DESCRIPTION
			            "Memory Location"
			            ::= { memHealthEntry 2 } 

		            memHealthStateLevel OBJECT-TYPE   
			            SYNTAX DisplayString
			            ACCESS read-only
			            STATUS current
			            DESCRIPTION
			            "Memory State Level"
			            ::= { memHealthEntry 3 } 

		            memHealthTemp OBJECT-TYPE   
			            SYNTAX DisplayString
			            ACCESS read-only
			            STATUS current
			            DESCRIPTION
			            "Memory TEMP"
			            ::= { memHealthEntry 4 }
			            
		            memHealthWorkFrequency OBJECT-TYPE   
			            SYNTAX DisplayString
			            ACCESS read-only
			            STATUS current
			            DESCRIPTION
			            "Memory WorkFrequency"
			            ::= { memHealthEntry 5 }
			            			               
		            memHealthState OBJECT-TYPE   
			            SYNTAX DisplayString
			            ACCESS read-only
			            STATUS current
			            DESCRIPTION
			            "Memory State"
			            ::= { memHealthEntry 6 }

    hddHealth OBJECT IDENTIFIER                ::=  { serverHealth 5 }
    			            
		    hddHealthAllStatus OBJECT-TYPE   
			    SYNTAX DisplayString
			    ACCESS read-only
			    STATUS current
			    DESCRIPTION
			    ""
			    ::= { hddHealth 1 }  
			     
        hddHealthTable OBJECT-TYPE
          SYNTAX  SEQUENCE OF HddHealthEntry
          ACCESS  not-accessible
          STATUS  mandatory
          ::= { hddHealth 2 }

            hddHealthEntry OBJECT-TYPE
              SYNTAX  HddHealthEntry
              ACCESS  not-accessible
              STATUS  mandatory
              INDEX   { hddHealthIndex }
              ::= { hddHealthTable 1 }

            HddHealthEntry ::= SEQUENCE {
              hddHealthIndex                      INTEGER,
              hddHealthStateLevel                 DisplayString,
              hddHealthState                      DisplayString  } 

		            hddHealthIndex OBJECT-TYPE   
			            SYNTAX INTEGER
			            ACCESS read-only
			            STATUS current
			            DESCRIPTION
			            ""
			            ::= { hddHealthEntry 1 } 


		            hddHealthStateLevel OBJECT-TYPE   
			            SYNTAX DisplayString
			            ACCESS read-only
			            STATUS current
			            DESCRIPTION
			            ""
			            ::= { hddHealthEntry 3 } 
			            			               			            

		            hddHealthState OBJECT-TYPE   
			            SYNTAX DisplayString
			            ACCESS read-only
			            STATUS current
			            DESCRIPTION
			            ""
			            ::= { hddHealthEntry 5 } 

    fanHealth OBJECT IDENTIFIER                ::=  { serverHealth 6 }
    			            
		    fanHealthAllStatus OBJECT-TYPE   
			    SYNTAX DisplayString
			    ACCESS read-only
			    STATUS current
			    DESCRIPTION
			    ""
			    ::= { fanHealth 1 }  
			     
        fanHealthTable OBJECT-TYPE
          SYNTAX  SEQUENCE OF FanHealthEntry
          ACCESS  not-accessible
          STATUS  mandatory
          ::= { fanHealth 2 }

            fanHealthEntry OBJECT-TYPE
              SYNTAX  FanHealthEntry
              ACCESS  not-accessible
              STATUS  mandatory
              INDEX   { fanHealthIndex }
              ::= { fanHealthTable 1 }

            FanHealthEntry ::= SEQUENCE {
              fanHealthIndex                      INTEGER,
              fanHealthLocation                   DisplayString,
              fanHealthStateLevel                 DisplayString,
              fanHealthDutyCycle                  DisplayString,
              fanHealthSpeed                      DisplayString,
              fanHealthState                      DisplayString  } 

		            fanHealthIndex OBJECT-TYPE   
			            SYNTAX INTEGER
			            ACCESS read-only
			            STATUS current
			            DESCRIPTION
			            ""
			            ::= { fanHealthEntry 1 } 

		            fanHealthLocation OBJECT-TYPE   
			            SYNTAX DisplayString
			            ACCESS read-only
			            STATUS current
			            DESCRIPTION
			            ""
			            ::= { fanHealthEntry 2 } 

		            fanHealthStateLevel OBJECT-TYPE   
			            SYNTAX DisplayString
			            ACCESS read-only
			            STATUS current
			            DESCRIPTION
			            ""
			            ::= { fanHealthEntry 3 } 
			            			               
		            fanHealthDutyCycle OBJECT-TYPE   
			            SYNTAX DisplayString
			            ACCESS read-only
			            STATUS current
			            DESCRIPTION
			            ""
			            ::= { fanHealthEntry 4 } 					            

		            fanHealthSpeed OBJECT-TYPE   
			            SYNTAX DisplayString
			            ACCESS read-only
			            STATUS current
			            DESCRIPTION
			            ""
			            ::= { fanHealthEntry 5 } 	

		            fanHealthState OBJECT-TYPE   
			            SYNTAX DisplayString
			            ACCESS read-only
			            STATUS current
			            DESCRIPTION
			            ""
			            ::= { fanHealthEntry 6 } 	
			            			            
    psuHealth OBJECT IDENTIFIER                ::=  { serverHealth 7 }

		    psuHealthAllStatus OBJECT-TYPE   
			    SYNTAX DisplayString
			    ACCESS read-only
			    STATUS current
			    DESCRIPTION
			    ""
			    ::= { psuHealth 1 }  
			     
        psuHealthTable OBJECT-TYPE
          SYNTAX  SEQUENCE OF PsuHealthEntry
          ACCESS  not-accessible
          STATUS  mandatory
          ::= { psuHealth 2 }

            psuHealthEntry OBJECT-TYPE
              SYNTAX  PsuHealthEntry
              ACCESS  not-accessible
              STATUS  mandatory
              INDEX   { psuHealthIndex }
              ::= { psuHealthTable 1 }

            PsuHealthEntry ::= SEQUENCE {
              psuHealthIndex                      INTEGER,
              psuHealthLocation                   DisplayString,
              psuHealthStateLevel                 DisplayString,
              psuHealthVIN                        DisplayString,
              psuHealthIIN                        DisplayString,
              psuHealthPIN                        DisplayString,
              psuHealthVOUT                       DisplayString,
              psuHealthIOUT                       DisplayString,              
              psuHealthPOUT                       DisplayString,
              psuHealthHeatsinkTemp               DisplayString,                                                                      
              psuHealthAmbientTemp                DisplayString,              
              psuHealthFanSpeed                   DisplayString,
              psuHealthState                      DisplayString } 

		            psuHealthIndex OBJECT-TYPE   
			            SYNTAX INTEGER
			            ACCESS read-only
			            STATUS current
			            DESCRIPTION
			            ""
			            ::= { psuHealthEntry 1 } 

		            psuHealthLocation OBJECT-TYPE   
			            SYNTAX DisplayString
			            ACCESS read-only
			            STATUS current
			            DESCRIPTION
			            ""
			            ::= { psuHealthEntry 2 } 

		            psuHealthStateLevel OBJECT-TYPE   
			            SYNTAX DisplayString
			            ACCESS read-only
			            STATUS current
			            DESCRIPTION
			            ""
			            ::= { psuHealthEntry 3 } 
			            			               
		            psuHealthVIN OBJECT-TYPE   
			            SYNTAX DisplayString
			            ACCESS read-only
			            STATUS current
			            DESCRIPTION
			            ""
			            ::= { psuHealthEntry 4 } 

		            psuHealthIIN OBJECT-TYPE   
			            SYNTAX DisplayString
			            ACCESS read-only
			            STATUS current
			            DESCRIPTION
			            ""
			            ::= { psuHealthEntry 5 } 

		            psuHealthPIN OBJECT-TYPE   
			            SYNTAX DisplayString
			            ACCESS read-only
			            STATUS current
			            DESCRIPTION
			            ""
			            ::= { psuHealthEntry 6 } 

		            psuHealthVOUT OBJECT-TYPE   
			            SYNTAX DisplayString
			            ACCESS read-only
			            STATUS current
			            DESCRIPTION
			            ""
			            ::= { psuHealthEntry 7 } 
			            			               
		            psuHealthIOUT OBJECT-TYPE   
			            SYNTAX DisplayString
			            ACCESS read-only
			            STATUS current
			            DESCRIPTION
			            ""
			            ::= { psuHealthEntry 8 } 

		            psuHealthPOUT OBJECT-TYPE   
			            SYNTAX DisplayString
			            ACCESS read-only
			            STATUS current
			            DESCRIPTION
			            ""
			            ::= { psuHealthEntry 9 } 

		            psuHealthHeatsinkTemp OBJECT-TYPE   
			            SYNTAX DisplayString
			            ACCESS read-only
			            STATUS current
			            DESCRIPTION
			            ""
			            ::= { psuHealthEntry 10 } 

		            psuHealthAmbientTemp OBJECT-TYPE   
			            SYNTAX DisplayString
			            ACCESS read-only
			            STATUS current
			            DESCRIPTION
			            ""
			            ::= { psuHealthEntry 11 } 
			            			               
		            psuHealthFanSpeed OBJECT-TYPE   
			            SYNTAX DisplayString
			            ACCESS read-only
			            STATUS current
			            DESCRIPTION
			            ""
			            ::= { psuHealthEntry 12 } 

		            psuHealthState OBJECT-TYPE   
			            SYNTAX DisplayString
			            ACCESS read-only
			            STATUS current
			            DESCRIPTION
			            ""
			            ::= { psuHealthEntry 13 } 

			            



--    ****** START trap Location ******************************* 

  trapGroup OBJECT IDENTIFIER ::= { bmc 500 } 
  
  trapVar OBJECT IDENTIFIER ::= { trapGroup 1 }

    trapSeq OBJECT-TYPE
      SYNTAX INTEGER
      MAX-ACCESS read-only
      STATUS current
      DESCRIPTION
        "Trap sequence"
      ::= { trapVar 1 }
      
    trapSensorName OBJECT-TYPE
      SYNTAX DisplayString
      MAX-ACCESS read-only
      STATUS current
      DESCRIPTION
        "Trap sensor name"
      ::= { trapVar 2 }   
      
    trapEvent OBJECT-TYPE
      SYNTAX DisplayString
      MAX-ACCESS read-only
      STATUS current
      DESCRIPTION
        "Trap description "
      ::= { trapVar 3 }
      
    trapSeverity OBJECT-TYPE
      SYNTAX INTEGER
              {
        ok(1),
        minor(2),
        major(3),
        critical(4)
        }
      MAX-ACCESS read-only
      STATUS current
      DESCRIPTION
        "Trap severity
        1  - ok,
        2  - minor,
        3  - major,
        4  - critical."
      ::= { trapVar 4 }
      
    trapEventCode OBJECT-TYPE
      SYNTAX DisplayString
      MAX-ACCESS read-only
      STATUS current
      DESCRIPTION
        "Trap EventCode"
      ::= { trapVar 5 } 
      
      trapEventData2 OBJECT-TYPE
      SYNTAX INTEGER
      MAX-ACCESS read-only
      STATUS current
      DESCRIPTION
        "Trap Event Data 2"
      ::= { trapVar 6 }
      
    trapEventData3 OBJECT-TYPE
      SYNTAX INTEGER
      MAX-ACCESS read-only
      STATUS current
      DESCRIPTION
        "Trap Event Data 3"
      ::= { trapVar 7 } 
      
    trapServerIdentity OBJECT-TYPE
      SYNTAX DisplayString
      MAX-ACCESS read-only
      STATUS current
      DESCRIPTION
        "Trap Sever Identity"
      ::= { trapVar 8 }
      
    trapLocation OBJECT-TYPE
      SYNTAX DisplayString
      MAX-ACCESS read-only
      STATUS current
      DESCRIPTION
        "Trap location"
      ::= { trapVar 9 }

    trapTime OBJECT-TYPE
      SYNTAX DisplayString
      MAX-ACCESS read-only
      STATUS current
      DESCRIPTION
        "Trap time"
      ::= { trapVar 10 }
  
  serverAlertTrapGroup OBJECT IDENTIFIER ::= { trapGroup 10 }

    ariTemperature OBJECT IDENTIFIER ::= {serverAlertTrapGroup 1} 


	 alerttempLowerNonCriticalGoingLow NOTIFICATION-TYPE
      OBJECTS { trapSeq, trapSensorName, trapEvent, trapSeverity, trapEventCode, trapServerIdentity, trapLocation, trapTime } 
      STATUS  current
      DESCRIPTION
              "temp Lower Non Critical Going Low"
      ::= { ariTemperature 1 }
	  
	 alerttempLowerNonCriticalGoingLowDeassert NOTIFICATION-TYPE
      OBJECTS { trapSeq, trapSensorName, trapEvent, trapSeverity, trapEventCode, trapServerIdentity, trapLocation, trapTime } 
      STATUS  current
      DESCRIPTION
              "temp Lower Non Critical Going Low Deassert"
      ::= { ariTemperature 2 }	  
	 
	alerttempLowerCriticalGoingLow NOTIFICATION-TYPE
      OBJECTS { trapSeq, trapSensorName, trapEvent, trapSeverity, trapEventCode, trapServerIdentity, trapLocation, trapTime } 
      STATUS  current
      DESCRIPTION
              "temp Lower Critical Going Low"
      ::= { ariTemperature 33 }
	  
	alerttempLowerCriticalGoingLowDeassert NOTIFICATION-TYPE
      OBJECTS { trapSeq, trapSensorName, trapEvent, trapSeverity, trapEventCode, trapServerIdentity, trapLocation, trapTime } 
      STATUS  current
      DESCRIPTION
              "temp Lower Critical Going Low Deassert"
      ::= { ariTemperature 34 }

	alerttempLowerNonRecoverlGoingLow NOTIFICATION-TYPE
      OBJECTS { trapSeq, trapSensorName, trapEvent, trapSeverity, trapEventCode, trapServerIdentity, trapLocation, trapTime } 
      STATUS  current
      DESCRIPTION
              "temp Lower Non-Recoverable Going Low"
      ::= { ariTemperature 65 }
	  
	alerttempLowerNonRecoverlGoingLowDeassert NOTIFICATION-TYPE
      OBJECTS { trapSeq, trapSensorName, trapEvent, trapSeverity, trapEventCode, trapServerIdentity, trapLocation, trapTime } 
      STATUS  current
      DESCRIPTION
              "temp Lower Non-Recoverable Going Low Deassert"
      ::= { ariTemperature 66 }	  

	alerttempUpperNonCriticalGoingHigh NOTIFICATION-TYPE
      OBJECTS { trapSeq, trapSensorName, trapEvent, trapSeverity, trapEventCode, trapServerIdentity, trapLocation, trapTime } 
      STATUS  current
      DESCRIPTION
              "temp Upper Non-Critical Going High"
      ::= { ariTemperature 113 }
	  
	alerttempUpperNonCriticalGoingHighDeassert NOTIFICATION-TYPE
      OBJECTS { trapSeq, trapSensorName, trapEvent, trapSeverity, trapEventCode, trapServerIdentity, trapLocation, trapTime } 
      STATUS  current
      DESCRIPTION
              "temp Upper Non-Critical Going High Deassert"
      ::= { ariTemperature 114 }	  

	alerttempUpperCriticalGoingHigh NOTIFICATION-TYPE
      OBJECTS { trapSeq, trapSensorName, trapEvent, trapSeverity, trapEventCode, trapServerIdentity, trapLocation, trapTime } 
      STATUS  current
      DESCRIPTION
              "temp Upper Critical Going High"
      ::= { ariTemperature 145 }
	  
	alerttempUpperCriticalGoingHighDeassert NOTIFICATION-TYPE
      OBJECTS { trapSeq, trapSensorName, trapEvent, trapSeverity, trapEventCode, trapServerIdentity, trapLocation, trapTime } 
      STATUS  current
      DESCRIPTION
              "temp Upper Critical Going High deassert"
      ::= { ariTemperature 146 }	  

    alerttempUpperNonRecoverGoingHigh NOTIFICATION-TYPE
      OBJECTS { trapSeq, trapSensorName, trapEvent, trapSeverity, trapEventCode, trapServerIdentity, trapLocation, trapTime } 
      STATUS  current
      DESCRIPTION
              "temp Upper Non-Recoverable Going High"
      ::= { ariTemperature 177 }
	  
    alerttempUpperNonRecoverGoingHighDeassert NOTIFICATION-TYPE
      OBJECTS { trapSeq, trapSensorName, trapEvent, trapSeverity, trapEventCode, trapServerIdentity, trapLocation, trapTime } 
      STATUS  current
      DESCRIPTION
              "temp Upper Non-Recoverable Going High Deassert"
      ::= { ariTemperature 178 }

    ariVoltage OBJECT IDENTIFIER ::= {serverAlertTrapGroup 2} 

	alertvoltageLowerNonCriticalGoingLow NOTIFICATION-TYPE
      OBJECTS { trapSeq, trapSensorName, trapEvent, trapSeverity, trapEventCode, trapServerIdentity, trapLocation, trapTime } 
      STATUS  current
      DESCRIPTION
              "voltage Lower Non Critical Going Low"
      ::= { ariVoltage 1 }   
	  
	alertvoltageLowerNonCriticalGoingLowDeassert NOTIFICATION-TYPE
      OBJECTS { trapSeq, trapSensorName, trapEvent, trapSeverity, trapEventCode, trapServerIdentity, trapLocation, trapTime } 
      STATUS  current
      DESCRIPTION
              "voltage Lower Non Critical Going Low Deassert"
      ::= { ariVoltage 2 }	  

	  
	alertvoltageLowerNonCriticalGoingHighDeassert NOTIFICATION-TYPE
      OBJECTS { trapSeq, trapSensorName, trapEvent, trapSeverity, trapEventCode, trapServerIdentity, trapLocation, trapTime } 
      STATUS  current
      DESCRIPTION
              "voltage Lower Non-Critical Going High "
      ::= { ariVoltage 18 }   
	  

	alertvoltageLowerCriticalGoingLow NOTIFICATION-TYPE
      OBJECTS { trapSeq, trapSensorName, trapEvent, trapSeverity, trapEventCode, trapServerIdentity, trapLocation, trapTime } 
      STATUS  current
      DESCRIPTION
              "voltage Lower Critical Going Low"
      ::= { ariVoltage 33 }   
	  
	alertvoltageLowerCriticalGoingLowDeassert NOTIFICATION-TYPE
      OBJECTS { trapSeq, trapSensorName, trapEvent, trapSeverity, trapEventCode, trapServerIdentity, trapLocation, trapTime } 
      STATUS  current
      DESCRIPTION
              "voltage Lower Critical Going Low Deassert"
      ::= { ariVoltage 34 }	  


	alertvoltageLowerNonRecoverGoingLow NOTIFICATION-TYPE
      OBJECTS { trapSeq, trapSensorName, trapEvent, trapSeverity, trapEventCode, trapServerIdentity, trapLocation, trapTime } 
      STATUS  current
      DESCRIPTION
              "voltage Lower Non-Recoverable Going Low"
      ::= { ariVoltage 65 }
	  
	alertvoltageLowerNonRecoverGoingLowDeassert NOTIFICATION-TYPE
      OBJECTS { trapSeq, trapSensorName, trapEvent, trapSeverity, trapEventCode, trapServerIdentity, trapLocation, trapTime } 
      STATUS  current
      DESCRIPTION
              "voltage Lower Non-Recoverable Going Low Deassert"
      ::= { ariVoltage 66 }

	alertvoltageUpperNonCriticalGoingHigh NOTIFICATION-TYPE
      OBJECTS { trapSeq, trapSensorName, trapEvent, trapSeverity, trapEventCode, trapServerIdentity, trapLocation, trapTime } 
      STATUS  current
      DESCRIPTION
              "voltage Upper Non-Critical Going High"
      ::= { ariVoltage 113 }
	  
	alertvoltageUpperNonCriticalGoingHighDeassert NOTIFICATION-TYPE
      OBJECTS { trapSeq, trapSensorName, trapEvent, trapSeverity, trapEventCode, trapServerIdentity, trapLocation, trapTime } 
      STATUS  current
      DESCRIPTION
              "voltage Upper Non-Critical Going High Deassert"
      ::= { ariVoltage 114 }	  
 
	alertvoltageUpperCriticalGoingHigh NOTIFICATION-TYPE
      OBJECTS { trapSeq, trapSensorName, trapEvent, trapSeverity, trapEventCode, trapServerIdentity, trapLocation, trapTime } 
      STATUS  current
      DESCRIPTION
              "voltage Upper Critical Going High"
      ::= { ariVoltage 145 }
	  
	alertvoltageUpperCriticalGoingHighDeassert NOTIFICATION-TYPE
      OBJECTS { trapSeq, trapSensorName, trapEvent, trapSeverity, trapEventCode, trapServerIdentity, trapLocation, trapTime } 
      STATUS  current
      DESCRIPTION
              "voltage Upper Critical Going High Deassert"
      ::= { ariVoltage 146 }	  

	alertvoltageUpperNonRecoverGoingHigh NOTIFICATION-TYPE
      OBJECTS { trapSeq, trapSensorName, trapEvent, trapSeverity, trapEventCode, trapServerIdentity, trapLocation, trapTime } 
      STATUS  current
      DESCRIPTION
              "voltage Upper Non-Recoverable Going High"
      ::= { ariVoltage 177 }
	  
	alertvoltageUpperNonRecoverGoingHighDeassert NOTIFICATION-TYPE
      OBJECTS { trapSeq, trapSensorName, trapEvent, trapSeverity, trapEventCode, trapServerIdentity, trapLocation, trapTime } 
      STATUS  current
      DESCRIPTION
              "voltage Upper Non-Recoverable Going High Deassert"
      ::= { ariVoltage 178 }	  

    ariCurrent OBJECT IDENTIFIER ::= {serverAlertTrapGroup 3}

	currentLowerNonCriticalGoingLow NOTIFICATION-TYPE
      OBJECTS { trapSeq, trapSensorName, trapEvent, trapSeverity, trapEventCode, trapServerIdentity, trapLocation, trapTime } 
      STATUS  current
      DESCRIPTION
              "Current Lower Non Critical Going Low"
      ::= { ariCurrent 1 }


  currentLowerNonCriticalGoingLowDeassert NOTIFICATION-TYPE
      OBJECTS { trapSeq, trapSensorName, trapEvent, trapSeverity, trapEventCode, trapServerIdentity, trapLocation, trapTime } 
      STATUS  current
      DESCRIPTION
              "Current Lower Non Critical Going Low Deassert"
      ::= { ariCurrent 2 }
	  
	currentLowerCriticalGoingLow NOTIFICATION-TYPE
      OBJECTS { trapSeq, trapSensorName, trapEvent, trapSeverity, trapEventCode, trapServerIdentity, trapLocation, trapTime } 
      STATUS  current
      DESCRIPTION
              "Current Lower Critical Going Low"
      ::= { ariCurrent 33 }


  currentLowerCriticalGoingLowDeassert NOTIFICATION-TYPE
      OBJECTS { trapSeq, trapSensorName, trapEvent, trapSeverity, trapEventCode, trapServerIdentity, trapLocation, trapTime } 
      STATUS  current
      DESCRIPTION
              "Current Lower Critical Going Low Deassert"
      ::= { ariCurrent 34 }
	  
	currentLowerNonRecoverGoingLow NOTIFICATION-TYPE
      OBJECTS { trapSeq, trapSensorName, trapEvent, trapSeverity, trapEventCode, trapServerIdentity, trapLocation, trapTime } 
      STATUS  current
      DESCRIPTION
              "Current Lower Non-Recoverable Going Low"
      ::= { ariCurrent 65 }

  currentLowerNonRecoverGoingLowDeassert NOTIFICATION-TYPE
      OBJECTS { trapSeq, trapSensorName, trapEvent, trapSeverity, trapEventCode, trapServerIdentity, trapLocation, trapTime } 
      STATUS  current
      DESCRIPTION
              "Current Lower Non-Recoverable Going Low Deassert"
      ::= { ariCurrent 66 }

	currentUpperNonCriticalGoingHigh NOTIFICATION-TYPE
      OBJECTS { trapSeq, trapSensorName, trapEvent, trapSeverity, trapEventCode, trapServerIdentity, trapLocation, trapTime } 
      STATUS  current
      DESCRIPTION
              "Current Upper Non-Critical Going High"
      ::= { ariCurrent 113 }
 
  currentUpperNonCriticalGoingHighDeassert NOTIFICATION-TYPE
      OBJECTS { trapSeq, trapSensorName, trapEvent, trapSeverity, trapEventCode, trapServerIdentity, trapLocation, trapTime } 
      STATUS  current
      DESCRIPTION
              "Current Upper Non-Critical Going High Deassert"
      ::= { ariCurrent 114 }
 
	currentUpperCriticalGoingHigh NOTIFICATION-TYPE
      OBJECTS { trapSeq, trapSensorName, trapEvent, trapSeverity, trapEventCode, trapServerIdentity, trapLocation, trapTime } 
      STATUS  current
      DESCRIPTION
              "Current Upper Critical Going High"
      ::= { ariCurrent 145 }

  currentUpperCriticalGoingHighDeassert NOTIFICATION-TYPE
      OBJECTS { trapSeq, trapSensorName, trapEvent, trapSeverity, trapEventCode, trapServerIdentity, trapLocation, trapTime } 
      STATUS  current
      DESCRIPTION
              "Current Upper Critical Going High Deassert"
      ::= { ariCurrent 146 }

	currentUpperNonRecoverGoingHigh NOTIFICATION-TYPE
      OBJECTS { trapSeq, trapSensorName, trapEvent, trapSeverity, trapEventCode, trapServerIdentity, trapLocation, trapTime } 
      STATUS  current
      DESCRIPTION
              "Current Upper Non-Recoverable Going High"
      ::= { ariCurrent 177 }

  currentUpperNonRecoverGoingHighDeassert NOTIFICATION-TYPE
      OBJECTS { trapSeq, trapSensorName, trapEvent, trapSeverity, trapEventCode, trapServerIdentity, trapLocation, trapTime } 
      STATUS  current
      DESCRIPTION
              "Current Upper Non-Recoverable Going High Deassert"
      ::= { ariCurrent 178 }

    ariFan OBJECT IDENTIFIER ::= {serverAlertTrapGroup 4} 

	alertfanSpeedLowerNonCriticalGoingLow NOTIFICATION-TYPE
      OBJECTS { trapSeq, trapSensorName, trapEvent, trapSeverity, trapEventCode, trapServerIdentity, trapLocation, trapTime } 
      STATUS  current
      DESCRIPTION
              "Fan speed Lower Non Critical Going Low"
      ::= { ariFan 1 }
	
    alertfanSpeedLowerNonCriticalGoingLowDeassert NOTIFICATION-TYPE
      OBJECTS { trapSeq, trapSensorName, trapEvent, trapSeverity, trapEventCode, trapServerIdentity, trapLocation, trapTime } 
      STATUS  current
      DESCRIPTION
              "Fan speed Lower Non Critical Going Low Deassert"
      ::= { ariFan 2 }


	alertfanSpeedLowerCriticalGoingLow NOTIFICATION-TYPE
      OBJECTS { trapSeq, trapSensorName, trapEvent, trapSeverity, trapEventCode, trapServerIdentity, trapLocation, trapTime } 
      STATUS  current
      DESCRIPTION
              "Fan speed Lower Critical Going Low"
      ::= { ariFan 33 }
	  
	  alertfanSpeedLowerCriticalGoingLowDeassert NOTIFICATION-TYPE
      OBJECTS { trapSeq, trapSensorName, trapEvent, trapSeverity, trapEventCode, trapServerIdentity, trapLocation, trapTime } 
      STATUS  current
      DESCRIPTION
              "Fan speed Lower Critical Going Low Deassert"
      ::= { ariFan 34 }  


	alertfanSpeedLowerNonRecoverGoingLow NOTIFICATION-TYPE
      OBJECTS { trapSeq, trapSensorName, trapEvent, trapSeverity, trapEventCode, trapServerIdentity, trapLocation, trapTime } 
      STATUS  current
      DESCRIPTION
              "Fan speed Lower Non-Recoverable Going Low"
      ::= { ariFan 65 }

  alertfanSpeedLowerNonRecoverGoingLowDeassert NOTIFICATION-TYPE
      OBJECTS { trapSeq, trapSensorName, trapEvent, trapSeverity, trapEventCode, trapServerIdentity, trapLocation, trapTime } 
      STATUS  current
      DESCRIPTION
              "Fan speed Lower Non-Recoverable Going Low Deassert"
      ::= { ariFan 66 }

	alertfanSpeedUpperNonCriticalGoingHigh NOTIFICATION-TYPE
      OBJECTS { trapSeq, trapSensorName, trapEvent, trapSeverity, trapEventCode, trapServerIdentity, trapLocation, trapTime } 
      STATUS  current
      DESCRIPTION
              "Fan speed Upper Non-Critical Going High"
      ::= { ariFan 113 }
	
   alertfanSpeedUpperNonCriticalGoingHighDeassert NOTIFICATION-TYPE
      OBJECTS { trapSeq, trapSensorName, trapEvent, trapSeverity, trapEventCode, trapServerIdentity, trapLocation, trapTime } 
      STATUS  current
      DESCRIPTION
              "Fan speed Upper Non-Critical Going High Deassert"
      ::= { ariFan 114 }
  
	alertfanSpeedUpperCriticalGoingHigh NOTIFICATION-TYPE
      OBJECTS { trapSeq, trapSensorName, trapEvent, trapSeverity, trapEventCode, trapServerIdentity, trapLocation, trapTime } 
      STATUS  current
      DESCRIPTION
              "Fan speed Upper Critical Going High"
      ::= { ariFan 145 }
	
 
  alertfanSpeedUpperCriticalGoingHighDeassert NOTIFICATION-TYPE
      OBJECTS { trapSeq, trapSensorName, trapEvent, trapSeverity, trapEventCode, trapServerIdentity, trapLocation, trapTime } 
      STATUS  current
      DESCRIPTION
              "Fan speed Upper Critical Going High Deassert"
      ::= { ariFan 146 }
  
	alertfanSpeedUpperNonRecoverGoingHigh NOTIFICATION-TYPE
      OBJECTS { trapSeq, trapSensorName, trapEvent, trapSeverity, trapEventCode, trapServerIdentity, trapLocation, trapTime } 
      STATUS  current
      DESCRIPTION
              "Fan speed Upper Non-Recoverable Going High"
      ::= { ariFan 177 }

  alertfanSpeedUpperNonRecoverGoingHighDeassert NOTIFICATION-TYPE
      OBJECTS { trapSeq, trapSensorName, trapEvent, trapSeverity, trapEventCode, trapServerIdentity, trapLocation, trapTime } 
      STATUS  current
      DESCRIPTION
              "Fan speed Upper Non-Recoverable Going High Deassert"
      ::= { ariFan 178 }
	  

  alertfanNotPresentStatus NOTIFICATION-TYPE
      OBJECTS { trapSeq, trapSensorName, trapEvent, trapSeverity, trapEventCode, trapServerIdentity, trapLocation, trapTime } 
      STATUS  current
      DESCRIPTION
              "Fan Absent"
      ::= { ariFan 1793 }
	  
  alertfanPresentStatus NOTIFICATION-TYPE
      OBJECTS { trapSeq, trapSensorName, trapEvent, trapSeverity, trapEventCode, trapServerIdentity, trapLocation, trapTime } 
      STATUS  current
      DESCRIPTION
              "Fan Present"
      ::= { ariFan 1809 }

  alertfanSpeedStatus NOTIFICATION-TYPE
      OBJECTS { trapSeq, trapSensorName, trapEvent, trapSeverity, trapEventCode, trapServerIdentity, trapLocation, trapTime } 
      STATUS  current
      DESCRIPTION
              "Fan Speed Too Low"
      ::= { ariFan 1825 }

  alertfanSpeedStatusDeassert NOTIFICATION-TYPE
      OBJECTS { trapSeq, trapSensorName, trapEvent, trapSeverity, trapEventCode, trapServerIdentity, trapLocation, trapTime } 
      STATUS  current
      DESCRIPTION
              "Fan Speed Too Low Deassert"
      ::= { ariFan 1826}


  alertfanHotPlugStatus NOTIFICATION-TYPE
      OBJECTS { trapSeq, trapSensorName, trapEvent, trapSeverity, trapEventCode, trapServerIdentity, trapLocation, trapTime } 
      STATUS  current
      DESCRIPTION
              "Fan Hot Plug"
      ::= { ariFan 2001 }

  alertfanHotPlugStatusDeassert NOTIFICATION-TYPE
      OBJECTS { trapSeq, trapSensorName, trapEvent, trapSeverity, trapEventCode, trapServerIdentity, trapLocation, trapTime } 
      STATUS  current
      DESCRIPTION
              "Fan Hot Plug Deassert"
      ::= { ariFan 2002 }	  
	  
    ariPhysicalSecurity OBJECT IDENTIFIER ::= {serverAlertTrapGroup 5} 
    
    alertChassisIntrusion NOTIFICATION-TYPE
      OBJECTS { trapSeq, trapSensorName, trapEvent, trapSeverity, trapEventCode, trapServerIdentity, trapLocation, trapTime } 
      STATUS  current
      DESCRIPTION
              "General Chassis Intrusion"
      ::= { ariPhysicalSecurity 1 }
	  
    alertChassisIntrusionLANLeashLost NOTIFICATION-TYPE
      OBJECTS { trapSeq, trapSensorName, trapEvent, trapSeverity, trapEventCode, trapServerIdentity, trapLocation, trapTime } 
      STATUS  current
      DESCRIPTION
              "General Chassis Intrusion"
      ::= { ariPhysicalSecurity 65 }	 

    alertChassisIntrusionLANLeashLostDeassert NOTIFICATION-TYPE
      OBJECTS { trapSeq, trapSensorName, trapEvent, trapSeverity, trapEventCode, trapServerIdentity, trapLocation, trapTime } 
      STATUS  current
      DESCRIPTION
              "General Chassis Intrusion deassert"
      ::= { ariPhysicalSecurity 66 }		  
  
    ariCPU OBJECT IDENTIFIER ::= {serverAlertTrapGroup 7} 
    
    alertCPUCATError NOTIFICATION-TYPE
      OBJECTS { trapSeq, trapSensorName, trapEvent, trapSeverity, trapEventCode, trapServerIdentity, trapLocation, trapTime }
      STATUS  current
      DESCRIPTION
              "CPU CAT error"
      ::= { ariCPU 1 }

    alertCPUCATErrorDeassert NOTIFICATION-TYPE
      OBJECTS { trapSeq, trapSensorName, trapEvent, trapSeverity, trapEventCode, trapServerIdentity, trapLocation, trapTime }
      STATUS  current
      DESCRIPTION
              "CPU CAT error deassert"
      ::= { ariCPU 2 }

    alertCPUThermalTrip NOTIFICATION-TYPE
      OBJECTS { trapSeq, trapSensorName, trapEvent, trapSeverity, trapEventCode, trapServerIdentity, trapLocation, trapTime }
      STATUS  current
      DESCRIPTION
              "CPU thermal trip"
      ::= { ariCPU 17 }

    alertCPUThermalTripDeassert NOTIFICATION-TYPE
      OBJECTS { trapSeq, trapSensorName, trapEvent, trapSeverity, trapEventCode, trapServerIdentity, trapLocation, trapTime }
      STATUS  current
      DESCRIPTION
              "CPU thermal trip deassert"
      ::= { ariCPU 18 }

    alertCPUSelfTestFail NOTIFICATION-TYPE
      OBJECTS { trapSeq, trapSensorName, trapEvent, trapSeverity, trapEventCode, trapServerIdentity, trapLocation, trapTime }
      STATUS  current
      DESCRIPTION
              "CPU FRB1/BIST failure"
      ::= { ariCPU 33 }

    alertCPUSelfTestFailDeassert NOTIFICATION-TYPE
      OBJECTS { trapSeq, trapSensorName, trapEvent, trapSeverity, trapEventCode, trapServerIdentity, trapLocation, trapTime }
      STATUS  current
      DESCRIPTION
              "CPU FRB1/BIST failure deassert"
      ::= { ariCPU 34 }


    alertCPUCfgError NOTIFICATION-TYPE
      OBJECTS { trapSeq, trapSensorName, trapEvent, trapSeverity, trapEventCode, trapServerIdentity, trapLocation, trapTime }
      STATUS  current
      DESCRIPTION
              "CPU configure error"
      ::= { ariCPU 81 }

    alertCPUCfgErrorDeassert NOTIFICATION-TYPE
      OBJECTS { trapSeq, trapSensorName, trapEvent, trapSeverity, trapEventCode, trapServerIdentity, trapLocation, trapTime }
      STATUS  current
      DESCRIPTION
              "CPU configure error deassert"
      ::= { ariCPU 82 }

    alertCPUPresence NOTIFICATION-TYPE
      OBJECTS { trapSeq, trapSensorName, trapEvent, trapSeverity, trapEventCode, trapServerIdentity, trapLocation, trapTime }
      STATUS  current
      DESCRIPTION
              "CPU Presence"
      ::= { ariCPU 113 }

    alertCPUPresenceDeassert NOTIFICATION-TYPE
      OBJECTS { trapSeq, trapSensorName, trapEvent, trapSeverity, trapEventCode, trapServerIdentity, trapLocation, trapTime }
      STATUS  current
      DESCRIPTION
              "CPU Presence deassert"
      ::= { ariCPU 114 }

    alertCPUOffline NOTIFICATION-TYPE
      OBJECTS { trapSeq, trapSensorName, trapEvent, trapSeverity, trapEventCode, trapServerIdentity, trapLocation, trapTime }
      STATUS  current
      DESCRIPTION
              "CPU offline"
      ::= { ariCPU 129 }

    alertCPUOfflineDeassert NOTIFICATION-TYPE
      OBJECTS { trapSeq, trapSensorName, trapEvent, trapSeverity, trapEventCode, trapServerIdentity, trapLocation, trapTime }
      STATUS  current
      DESCRIPTION
              "CPU offline deassert"
      ::= { ariCPU 130 }

    alertCPUAutoThrottled NOTIFICATION-TYPE
      OBJECTS { trapSeq, trapSensorName, trapEvent, trapSeverity, trapEventCode, trapServerIdentity, trapLocation, trapTime }
      STATUS  current
      DESCRIPTION
              "CPU Automatically Throttled assert"
      ::= { ariCPU 161 }

    alertCPUAutoThrottledDeassert NOTIFICATION-TYPE
      OBJECTS { trapSeq, trapSensorName, trapEvent, trapSeverity, trapEventCode, trapServerIdentity, trapLocation, trapTime }
      STATUS  current
      DESCRIPTION
              "CPU Automatically Throttled deassert"
      ::= { ariCPU 162 }

    alertCPUMCE NOTIFICATION-TYPE
      OBJECTS { trapSeq, trapSensorName, trapEvent, trapSeverity, trapEventCode, trapServerIdentity, trapLocation, trapTime }
      STATUS  current
      DESCRIPTION
              "CPU MCE occured"
      ::= { ariCPU 177 }

    alertCPUMCEDeassert NOTIFICATION-TYPE
      OBJECTS { trapSeq, trapSensorName, trapEvent, trapSeverity, trapEventCode, trapServerIdentity, trapLocation, trapTime }
      STATUS  current
      DESCRIPTION
              "CPU MCE deassert"
      ::= { ariCPU 178 }  

    alertVMSELinkFail NOTIFICATION-TYPE
      OBJECTS { trapSeq, trapSensorName, trapEvent, trapSeverity, trapEventCode, trapServerIdentity, trapLocation, trapTime }
      STATUS  current
      DESCRIPTION
              "CPU VMSE link failure in mirror mode"
      ::= { ariCPU 193 }

    alertVMSELinkFailDeassert NOTIFICATION-TYPE
      OBJECTS { trapSeq, trapSensorName, trapEvent, trapSeverity, trapEventCode, trapServerIdentity, trapLocation, trapTime }
      STATUS  current
      DESCRIPTION
              "CPU VMSE link failure in mirror mode deassert"
      ::= { ariCPU 194 }

  
    ariPowerSupply OBJECT IDENTIFIER ::= {serverAlertTrapGroup 8}
    
  powerLowerNonCriticalGoingLow NOTIFICATION-TYPE
      OBJECTS { trapSeq, trapSensorName, trapEvent, trapSeverity, trapEventCode, trapServerIdentity, trapLocation, trapTime } 
      STATUS  current
      DESCRIPTION
              "Power Lower Non Critical Going Low"
      ::= { ariPowerSupply 1 }
	  
  powerLowerNonCriticalGoingLowDeassert NOTIFICATION-TYPE
      OBJECTS { trapSeq, trapSensorName, trapEvent, trapSeverity, trapEventCode, trapServerIdentity, trapLocation, trapTime } 
      STATUS  current
      DESCRIPTION
              " Power Lower Non Critical Going Low Deassert"
      ::= { ariPowerSupply 2 }	  

  powerLowerCriticalGoingLow NOTIFICATION-TYPE
      OBJECTS { trapSeq, trapSensorName, trapEvent, trapSeverity, trapEventCode, trapServerIdentity, trapLocation, trapTime } 
      STATUS  current
      DESCRIPTION
              " Power Lower Critical Going Low"
      ::= { ariPowerSupply 33 }
	  
  powerLowerCriticalGoingLowDeassert NOTIFICATION-TYPE
      OBJECTS { trapSeq, trapSensorName, trapEvent, trapSeverity, trapEventCode, trapServerIdentity, trapLocation, trapTime } 
      STATUS  current
      DESCRIPTION
              " Power Lower Critical Going Low Deassert"
      ::= { ariPowerSupply 34 }
	  
    powerLowerNonRecoverGoingLow NOTIFICATION-TYPE
      OBJECTS { trapSeq, trapSensorName, trapEvent, trapSeverity, trapEventCode, trapServerIdentity, trapLocation, trapTime } 
      STATUS  current
      DESCRIPTION
              " Power Lower Non-Recoverable Going Low"
      ::= { ariPowerSupply 65 }

    powerLowerNonRecoverGoingLowDeassert NOTIFICATION-TYPE
      OBJECTS { trapSeq, trapSensorName, trapEvent, trapSeverity, trapEventCode, trapServerIdentity, trapLocation, trapTime } 
      STATUS  current
      DESCRIPTION
              " Power Lower Non-Recoverable Going Low Deassert"
      ::= { ariPowerSupply 66 }

    powerUpperNonCriticalGoingHigh NOTIFICATION-TYPE
      OBJECTS { trapSeq, trapSensorName, trapEvent, trapSeverity, trapEventCode, trapServerIdentity, trapLocation, trapTime } 
      STATUS  current
      DESCRIPTION
              " Power Upper Non-Critical Going High"
      ::= { ariPowerSupply 113 }
 
    powerUpperNonCriticalGoingHighDeassert NOTIFICATION-TYPE
      OBJECTS { trapSeq, trapSensorName, trapEvent, trapSeverity, trapEventCode, trapServerIdentity, trapLocation, trapTime } 
      STATUS  current
      DESCRIPTION
              " Power Upper Non-Critical Going High Deassert"
      ::= { ariPowerSupply 114 }

    powerUpperCriticalGoingHigh NOTIFICATION-TYPE
      OBJECTS { trapSeq, trapSensorName, trapEvent, trapSeverity, trapEventCode, trapServerIdentity, trapLocation, trapTime } 
      STATUS  current
      DESCRIPTION
              " Power Upper Critical Going High"
      ::= { ariPowerSupply 145 }

    powerUpperCriticalGoingHighDeassert NOTIFICATION-TYPE
      OBJECTS { trapSeq, trapSensorName, trapEvent, trapSeverity, trapEventCode, trapServerIdentity, trapLocation, trapTime } 
      STATUS  current
      DESCRIPTION
              " Power Upper Critical Going High Deassert"
      ::= { ariPowerSupply 146 }

    powerUpperNonRecoverGoingHigh NOTIFICATION-TYPE
      OBJECTS { trapSeq, trapSensorName, trapEvent, trapSeverity, trapEventCode, trapServerIdentity, trapLocation, trapTime } 
      STATUS  current
      DESCRIPTION
              " Power Upper Non-Recoverable Going High"
      ::= { ariPowerSupply 177 }

    powerUpperNonRecoverGoingHighDeassert NOTIFICATION-TYPE
      OBJECTS { trapSeq, trapSensorName, trapEvent, trapSeverity, trapEventCode, trapServerIdentity, trapLocation, trapTime } 
      STATUS  current
      DESCRIPTION
              " Power Upper Non-Recoverable Going High Deassert"
      ::= { ariPowerSupply 178 }

    alertPsuPresence NOTIFICATION-TYPE
      OBJECTS { trapSeq, trapSensorName, trapEvent, trapSeverity, trapEventCode, trapServerIdentity, trapLocation, trapTime }
      STATUS  current
      DESCRIPTION
              "Power Supply Presence"
      ::= { ariPowerSupply 28161 }

    alertPsuPresenceDeassert NOTIFICATION-TYPE
      OBJECTS { trapSeq, trapSensorName, trapEvent, trapSeverity, trapEventCode, trapServerIdentity, trapLocation, trapTime }
      STATUS  current
      DESCRIPTION
              "Power Supply Presence Deassert"
      ::= { ariPowerSupply 28162 }

    alertPsuFault NOTIFICATION-TYPE
      OBJECTS { trapSeq, trapSensorName, trapEvent, trapSeverity, trapEventCode, trapServerIdentity, trapLocation, trapTime }
      STATUS  current
      DESCRIPTION
              "Power Supply Fault"
      ::= { ariPowerSupply 28177 }

    alertPsuFaultDeassert NOTIFICATION-TYPE
      OBJECTS { trapSeq, trapSensorName, trapEvent, trapSeverity, trapEventCode, trapServerIdentity, trapLocation, trapTime }
      STATUS  current
      DESCRIPTION
              "Power Supply Fault Deassert"
      ::= { ariPowerSupply 28178 }


    alertPsuPredictiveFailure NOTIFICATION-TYPE
      OBJECTS { trapSeq, trapSensorName, trapEvent, trapSeverity, trapEventCode, trapServerIdentity, trapLocation, trapTime }
      STATUS  current
      DESCRIPTION
              "Power Supply Predictive Failure"
      ::= { ariPowerSupply 28193 }

    alertPsuPredictiveFailureDeassert NOTIFICATION-TYPE
      OBJECTS { trapSeq, trapSensorName, trapEvent, trapSeverity, trapEventCode, trapServerIdentity, trapLocation, trapTime }
      STATUS  current
      DESCRIPTION
              "Power Supply Predictive Failure Deassert"
      ::= { ariPowerSupply 28194 }

    alertPsuInputLost NOTIFICATION-TYPE
      OBJECTS { trapSeq, trapSensorName, trapEvent, trapSeverity, trapEventCode, trapServerIdentity, trapLocation, trapTime }
      STATUS  current
      DESCRIPTION
              "Power Supply Input Lost"
      ::= { ariPowerSupply 28209 }

    alertPsuInputLostDeassert NOTIFICATION-TYPE
      OBJECTS { trapSeq, trapSensorName, trapEvent, trapSeverity, trapEventCode, trapServerIdentity, trapLocation, trapTime }
      STATUS  current
      DESCRIPTION
              "Power Supply Input Lost Deassert"
      ::= { ariPowerSupply 28210 }
    

    alertPsuOutOfRange NOTIFICATION-TYPE
      OBJECTS { trapSeq, trapSensorName, trapEvent, trapSeverity, trapEventCode, trapServerIdentity, trapLocation, trapTime }
      STATUS  current
      DESCRIPTION
              "Power Supply Input lost or out-of-range"
      ::= { ariPowerSupply 28225 }

    alertPsuOutOfRangeDeassert NOTIFICATION-TYPE
      OBJECTS { trapSeq, trapSensorName, trapEvent, trapSeverity, trapEventCode, trapServerIdentity, trapLocation, trapTime }
      STATUS  current
      DESCRIPTION
              "Power Supply Input lost or out-of-range Deassert"
      ::= { ariPowerSupply 28226 }

    alertPsuOutOfRangeButPresent NOTIFICATION-TYPE
      OBJECTS { trapSeq, trapSensorName, trapEvent, trapSeverity, trapEventCode, trapServerIdentity, trapLocation, trapTime }
      STATUS  current
      DESCRIPTION
              "Power Supply Input Lost Or Out-of-range But Present"
      ::= { ariPowerSupply 28241 }

    alertPsuOutOfRangeButPresentDeassert NOTIFICATION-TYPE
      OBJECTS { trapSeq, trapSensorName, trapEvent, trapSeverity, trapEventCode, trapServerIdentity, trapLocation, trapTime }
      STATUS  current
      DESCRIPTION
              "Power Supply Input Lost Or Out-of-range But Present Deassert"
      ::= { ariPowerSupply 28242 }

    alertPsuConfigError NOTIFICATION-TYPE
      OBJECTS { trapSeq, trapSensorName, trapEvent, trapSeverity, trapEventCode, trapServerIdentity, trapLocation, trapTime }
      STATUS  current
      DESCRIPTION
              "Power Supply Configuration Error"
      ::= { ariPowerSupply 28257 }

    alertPsuConfigErrorDeassert NOTIFICATION-TYPE
      OBJECTS { trapSeq, trapSensorName, trapEvent, trapSeverity, trapEventCode, trapServerIdentity, trapLocation, trapTime }
      STATUS  current
      DESCRIPTION
              "Power Supply Configuration Error Deassert"
      ::= { ariPowerSupply 28258 }

    alertPsuStandbyState NOTIFICATION-TYPE
      OBJECTS { trapSeq, trapSensorName, trapEvent, trapSeverity, trapEventCode, trapServerIdentity, trapLocation, trapTime }
      STATUS  current
      DESCRIPTION
              "Power Supply Inactive (in standby state)"
      ::= { ariPowerSupply 28273 }

    alertPsuStandbyStateDeassert NOTIFICATION-TYPE
      OBJECTS { trapSeq, trapSensorName, trapEvent, trapSeverity, trapEventCode, trapServerIdentity, trapLocation, trapTime }
      STATUS  current
      DESCRIPTION
              "Power Supply Inactive (in standby state) Deassert"
      ::= { ariPowerSupply 28274 }


    alertPsuHotPlug NOTIFICATION-TYPE
      OBJECTS { trapSeq, trapSensorName, trapEvent, trapSeverity, trapEventCode, trapServerIdentity, trapLocation, trapTime }
      STATUS  current
      DESCRIPTION
              "Power Supply Unit Hot Plug"
      ::= { ariPowerSupply 28369 }

    alertPsuHotPlugDeassert NOTIFICATION-TYPE
      OBJECTS { trapSeq, trapSensorName, trapEvent, trapSeverity, trapEventCode, trapServerIdentity, trapLocation, trapTime }
      STATUS  current
      DESCRIPTION
              "Power Supply Unit Hot Plug Deassert"
      ::= { ariPowerSupply 28370 }

    alertPsuOverTemp NOTIFICATION-TYPE
      OBJECTS { trapSeq, trapSensorName, trapEvent, trapSeverity, trapEventCode, trapServerIdentity, trapLocation, trapTime }
      STATUS  current
      DESCRIPTION
              "Power Supply Unit Over Temperature"
      ::= { ariPowerSupply 28385 }

    alertPsuOverTempDeassert NOTIFICATION-TYPE
      OBJECTS { trapSeq, trapSensorName, trapEvent, trapSeverity, trapEventCode, trapServerIdentity, trapLocation, trapTime }
      STATUS  current
      DESCRIPTION
              "Power Supply Unit Over Temperature Deassert"
      ::= { ariPowerSupply 28386 }

    ariMemory OBJECT IDENTIFIER ::= {serverAlertTrapGroup 12}
    
    alertCorrectableECC NOTIFICATION-TYPE
      OBJECTS { trapSeq, trapSensorName, trapEvent, trapSeverity, trapEventCode, trapEventData2, trapEventData3, trapServerIdentity, trapLocation, trapTime }
      STATUS  current
      DESCRIPTION
              "memory correctable ECC error occurred"
      ::= { ariMemory 1 }

    alertCorrectableECCDeassert NOTIFICATION-TYPE
      OBJECTS { trapSeq, trapSensorName, trapEvent, trapSeverity, trapEventCode, trapEventData2, trapEventData3, trapServerIdentity, trapLocation, trapTime }
      STATUS  current
      DESCRIPTION
              "memory correctable ECC error deassert"
      ::= { ariMemory 2 }

    alertUncorrectableECC NOTIFICATION-TYPE
      OBJECTS { trapSeq, trapSensorName, trapEvent, trapSeverity, trapEventCode, trapEventData2, trapEventData3, trapServerIdentity, trapLocation, trapTime }
      STATUS  current
      DESCRIPTION
              "memory uncorrectable ECC error occurred"
      ::= { ariMemory 17 }

    alertUncorrectableECCDeassert NOTIFICATION-TYPE
      OBJECTS { trapSeq, trapSensorName, trapEvent, trapSeverity, trapEventCode, trapEventData2, trapEventData3, trapServerIdentity, trapLocation, trapTime }
      STATUS  current
      DESCRIPTION
              "memory uncorrectable ECC error deassert"
      ::= { ariMemory 18 }

    alertMemoryECCLimitation NOTIFICATION-TYPE
      OBJECTS { trapSeq, trapSensorName, trapEvent, trapSeverity, trapEventCode, trapEventData2, trapEventData3, trapServerIdentity, trapLocation, trapTime }
      STATUS  current
      DESCRIPTION
              "memory correctable ECC logging limit reached detected"
      ::= { ariMemory 81 }

    alertMemoryECCLimitationDeassert NOTIFICATION-TYPE
      OBJECTS { trapSeq, trapSensorName, trapEvent, trapSeverity, trapEventCode, trapEventData2, trapEventData3, trapServerIdentity, trapLocation, trapTime }
      STATUS  current
      DESCRIPTION
              "memory correctable ECC logging limit reached deassert"
      ::= { ariMemory 82 }


    alertMemoryPresence NOTIFICATION-TYPE
      OBJECTS { trapSeq, trapSensorName, trapEvent, trapSeverity, trapEventCode, trapEventData2, trapEventData3, trapServerIdentity, trapLocation, trapTime }
      STATUS  current
      DESCRIPTION
              "memory presence detected"
      ::= { ariMemory 97 }

    alertMemoryPresenceDeassert NOTIFICATION-TYPE
      OBJECTS { trapSeq, trapSensorName, trapEvent, trapSeverity, trapEventCode, trapEventData2, trapEventData3, trapServerIdentity, trapLocation, trapTime }
      STATUS  current
      DESCRIPTION
              "memory presence deassert"
      ::= { ariMemory 98 }


    alertMemoryCfgError NOTIFICATION-TYPE
      OBJECTS { trapSeq, trapSensorName, trapEvent, trapSeverity, trapEventCode, trapEventData2, trapEventData3, trapServerIdentity, trapLocation, trapTime }
      STATUS  current
      DESCRIPTION
              "memory config error detected"
      ::= { ariMemory 113 }

    alertMemoryCfgErrorDeassert NOTIFICATION-TYPE
      OBJECTS { trapSeq, trapSensorName, trapEvent, trapSeverity, trapEventCode, trapEventData2, trapEventData3, trapServerIdentity, trapLocation, trapTime }
      STATUS  current
      DESCRIPTION
              "memory config error deassert"
      ::= { ariMemory 114 }

    alertMemorySpare NOTIFICATION-TYPE
      OBJECTS { trapSeq, trapSensorName, trapEvent, trapSeverity, trapEventCode, trapEventData2, trapEventData3, trapServerIdentity, trapLocation, trapTime }
      STATUS  current
      DESCRIPTION
              "memory spare detected"
      ::= { ariMemory 129 }

    alertMemorySpareDeassert NOTIFICATION-TYPE
      OBJECTS { trapSeq, trapSensorName, trapEvent, trapSeverity, trapEventCode, trapEventData2, trapEventData3, trapServerIdentity, trapLocation, trapTime }
      STATUS  current
      DESCRIPTION
              "memory spare deassert"
      ::= { ariMemory 130 }

    alertMemoryOvertemp NOTIFICATION-TYPE
      OBJECTS { trapSeq, trapSensorName, trapEvent, trapSeverity, trapEventCode, trapEventData2, trapEventData3, trapServerIdentity, trapLocation, trapTime }
      STATUS  current
      DESCRIPTION
              "memory overtemperature detected"
      ::= { ariMemory 161 }

    alertMemoryOvertempDeassert NOTIFICATION-TYPE
      OBJECTS { trapSeq, trapSensorName, trapEvent, trapSeverity, trapEventCode, trapEventData2, trapEventData3, trapServerIdentity, trapLocation, trapTime }
      STATUS  current
      DESCRIPTION
              "memory overtemperature deassert"
      ::= { ariMemory 162 }

	alertMemoryMRCTraining NOTIFICATION-TYPE
      OBJECTS { trapSeq, trapSensorName, trapEvent, trapSeverity, trapEventCode, trapEventData2, trapEventData3, trapServerIdentity, trapLocation, trapTime }
      STATUS  current
      DESCRIPTION
              "Memory MRC training warning detected"
      ::= { ariMemory 177 }
	  
    alertMemoryMRC NOTIFICATION-TYPE
      OBJECTS { trapSeq, trapSensorName, trapEvent, trapSeverity, trapEventCode, trapEventData2, trapEventData3, trapServerIdentity, trapLocation, trapTime }
      STATUS  current
      DESCRIPTION
              "Memory MRC DRAM memtest errors detected"
      ::= { ariMemory 193 }

  
    ariHardDisk OBJECT IDENTIFIER ::= {serverAlertTrapGroup 13}
    
    alertHardDiskPresence NOTIFICATION-TYPE
      OBJECTS { trapSeq, trapSensorName, trapEvent, trapSeverity, trapEventCode, trapServerIdentity, trapLocation, trapTime }
      STATUS  current
      DESCRIPTION
              "Harddisk presence detected"
      ::= { ariHardDisk 1 }

    alertHardDiskPresenceDeassert NOTIFICATION-TYPE
      OBJECTS { trapSeq, trapSensorName, trapEvent, trapSeverity, trapEventCode, trapServerIdentity, trapLocation, trapTime }
      STATUS  current
      DESCRIPTION
              "Harddisk presence deassert"
      ::= { ariHardDisk 2 }

     alertHardDiskFault NOTIFICATION-TYPE
      OBJECTS { trapSeq, trapSensorName, trapEvent, trapSeverity, trapEventCode, trapServerIdentity, trapLocation, trapTime }
      STATUS  current
      DESCRIPTION
              "Harddisk fault detected"
      ::= { ariHardDisk 17 }

    alertHardDiskFaultDeassert NOTIFICATION-TYPE
      OBJECTS { trapSeq, trapSensorName, trapEvent, trapSeverity, trapEventCode, trapServerIdentity, trapLocation, trapTime }
      STATUS  current
      DESCRIPTION
              "Harddisk fault deassert"
      ::= { ariHardDisk 18 }

    alertHardDiskPredictiveFailure NOTIFICATION-TYPE
      OBJECTS { trapSeq, trapSensorName, trapEvent, trapSeverity, trapEventCode, trapServerIdentity, trapLocation, trapTime }
      STATUS  current
      DESCRIPTION
              "Hard disk predictive failure"
      ::= { ariHardDisk 33 }

    alertHardDiskPredictiveFailureDeassert NOTIFICATION-TYPE
      OBJECTS { trapSeq, trapSensorName, trapEvent, trapSeverity, trapEventCode, trapServerIdentity, trapLocation, trapTime }
      STATUS  current
      DESCRIPTION
              "Hard disk predictive failure deassert"
      ::= { ariHardDisk 34 }
    
    alertRAIDArrayFail NOTIFICATION-TYPE
      OBJECTS { trapSeq, trapSensorName, trapEvent, trapSeverity, trapEventCode, trapServerIdentity, trapLocation, trapTime }
      STATUS  current
      DESCRIPTION
              "RAID array fail detected"
      ::= { ariHardDisk 97 }

    alertRAIDArrayFailDeassert NOTIFICATION-TYPE
      OBJECTS { trapSeq, trapSensorName, trapEvent, trapSeverity, trapEventCode, trapServerIdentity, trapLocation, trapTime }
      STATUS  current
      DESCRIPTION
              "RAID array fail deassert"
      ::= { ariHardDisk 98 }

  alertRAIDRebuild NOTIFICATION-TYPE
      OBJECTS { trapSeq, trapSensorName, trapEvent, trapSeverity, trapEventCode, trapServerIdentity, trapLocation, trapTime }
      STATUS  current
      DESCRIPTION
              "RAID rebuild detected"
      ::= { ariHardDisk 113 }

    alertRAIDRebuildDeassert NOTIFICATION-TYPE
      OBJECTS { trapSeq, trapSensorName, trapEvent, trapSeverity, trapEventCode, trapServerIdentity, trapLocation, trapTime }
      STATUS  current
      DESCRIPTION
              "RAID rebuild deassert"
      ::= { ariHardDisk 114 }
    
  alertRAIDRebuildAborted NOTIFICATION-TYPE
      OBJECTS { trapSeq, trapSensorName, trapEvent, trapSeverity, trapEventCode, trapServerIdentity, trapLocation, trapTime }
      STATUS  current
      DESCRIPTION
              "RAID rebuild aborted detected"
      ::= { ariHardDisk 129 }
    
  alertRAIDRebuildAbortedDeassert NOTIFICATION-TYPE
      OBJECTS { trapSeq, trapSensorName, trapEvent, trapSeverity, trapEventCode, trapServerIdentity, trapLocation, trapTime }
      STATUS  current
      DESCRIPTION
              "RAID rebuild aborted deassert"
      ::= { ariHardDisk 130 }

  alertHardDiskHotplug NOTIFICATION-TYPE
      OBJECTS { trapSeq, trapSensorName, trapEvent, trapSeverity, trapEventCode, trapServerIdentity, trapLocation, trapTime }
      STATUS  current
      DESCRIPTION
              "Hard disk hot plug"
      ::= { ariHardDisk 209 }	  
	  
  alertHardDiskHotplugDeassert NOTIFICATION-TYPE
      OBJECTS { trapSeq, trapSensorName, trapEvent, trapSeverity, trapEventCode, trapServerIdentity, trapLocation, trapTime }
      STATUS  current
      DESCRIPTION
              "Hard disk hot plug deassert"
      ::= { ariHardDisk 210 }	
	  
    ariSysFWProgress OBJECT IDENTIFIER ::= {serverAlertTrapGroup 15} 
    
    alertSystemFirmwareHang NOTIFICATION-TYPE
      OBJECTS { trapSeq, trapSensorName, trapEvent, trapSeverity, trapEventCode, trapServerIdentity, trapLocation, trapTime }
      STATUS  current
      DESCRIPTION
              "System firmware hang"
      ::= { ariSysFWProgress 17 }

    alertSystemFirmwareHangDeassert NOTIFICATION-TYPE
      OBJECTS { trapSeq, trapSensorName, trapEvent, trapSeverity, trapEventCode, trapServerIdentity, trapLocation, trapTime }
      STATUS  current
      DESCRIPTION
              "System firmware hang deassert"
      ::= { ariSysFWProgress 18 }
    
    alertPS2USBFault NOTIFICATION-TYPE
      OBJECTS { trapSeq, trapSensorName, trapEvent, trapSeverity, trapEventCode, trapServerIdentity, trapLocation, trapTime }
      STATUS  current
      DESCRIPTION
              "Unrecoverable PS/2 or USB keyboard failure"
      ::= { ariSysFWProgress 1793 }

    alertPS2USBFaultDeassert NOTIFICATION-TYPE
      OBJECTS { trapSeq, trapSensorName, trapEvent, trapSeverity, trapEventCode, trapServerIdentity, trapLocation, trapTime }
      STATUS  current
      DESCRIPTION
              "Unrecoverable PS/2 or USB keyboard failure deassert"
      ::= { ariSysFWProgress 1794 }

    alertVideoControllerFault NOTIFICATION-TYPE
      OBJECTS { trapSeq, trapSensorName, trapEvent, trapSeverity, trapEventCode, trapServerIdentity, trapLocation, trapTime }
      STATUS  current
      DESCRIPTION
              "Unrecoverable video controller failure"
      ::= { ariSysFWProgress 2305 }

    alertVideoControllerFaultDeassert NOTIFICATION-TYPE
      OBJECTS { trapSeq, trapSensorName, trapEvent, trapSeverity, trapEventCode, trapServerIdentity, trapLocation, trapTime }
      STATUS  current
      DESCRIPTION
              "Unrecoverable video controller failure deassert"
      ::= { ariSysFWProgress 2306 }

    alertCPUVoltageMismatch NOTIFICATION-TYPE
      OBJECTS { trapSeq, trapSensorName, trapEvent, trapSeverity, trapEventCode, trapServerIdentity, trapLocation, trapTime }
      STATUS  current
      DESCRIPTION
              "CPU voltage mismatch"
      ::= { ariSysFWProgress 3073 }

    alertCPUVoltageMismatchDeassert NOTIFICATION-TYPE
      OBJECTS { trapSeq, trapSensorName, trapEvent, trapSeverity, trapEventCode, trapServerIdentity, trapLocation, trapTime }
      STATUS  current
      DESCRIPTION
              "CPU voltage mismatch deassert"
      ::= { ariSysFWProgress 3074 }
      
  
    ariSELStatus OBJECT IDENTIFIER ::= {serverAlertTrapGroup 16}  
    
    alertSELClearedAssert NOTIFICATION-TYPE
      OBJECTS { trapSeq, trapSensorName, trapEvent, trapSeverity, trapEventCode, trapServerIdentity, trapLocation, trapTime }
      STATUS  current
      DESCRIPTION
              "SEL log area is cleared"
      ::= { ariSELStatus 33 }
    
    alertSELAlmostFullAssert NOTIFICATION-TYPE
      OBJECTS { trapSeq, trapSensorName, trapEvent, trapSeverity, trapEventCode, trapServerIdentity, trapLocation, trapTime }
      STATUS  current
      DESCRIPTION
              "SEL almost full assert"
      ::= { ariSELStatus 81 }

    alertSELAlmostFullDeassert NOTIFICATION-TYPE
      OBJECTS { trapSeq, trapSensorName, trapEvent, trapSeverity, trapEventCode, trapServerIdentity, trapLocation, trapTime }
      STATUS  current
      DESCRIPTION
              "SEL almost full deassert"
      ::= { ariSELStatus 82 }

    ariSysEvent OBJECT IDENTIFIER ::= {serverAlertTrapGroup 18} 
    
    alertSysEventInstance NOTIFICATION-TYPE
      OBJECTS { trapSeq, trapSensorName, trapEvent, trapSeverity, trapEventCode, trapServerIdentity, trapLocation, trapTime }
      STATUS  current
      DESCRIPTION
              "PEF action"
      ::= { ariSysEvent 65 }

    alertSystemError NOTIFICATION-TYPE
      OBJECTS { trapSeq, trapSensorName, trapEvent, trapSeverity, trapEventCode, trapServerIdentity, trapLocation, trapTime }
      STATUS  current
      DESCRIPTION
              "System hang up/reset. For more information, see the background log"
      ::= { ariSysEvent 33 }

    alertSystemErrorDeassert NOTIFICATION-TYPE
      OBJECTS { trapSeq, trapSensorName, trapEvent, trapSeverity, trapEventCode, trapServerIdentity, trapLocation, trapTime }
      STATUS  current
      DESCRIPTION
              "System hang up/reset deassert"
      ::= { ariSysEvent 34 }

    alertTimestampClockSync NOTIFICATION-TYPE
      OBJECTS { trapSeq, trapSensorName, trapEvent, trapSeverity, trapEventCode, trapServerIdentity, trapLocation, trapTime }
      STATUS  current
      DESCRIPTION
              "timestamp clock sync"
      ::= { ariSysEvent 81 }

    ariCriticalInterrupt  OBJECT IDENTIFIER ::= {serverAlertTrapGroup 19} 
    
    alertNMI NOTIFICATION-TYPE
      OBJECTS { trapSeq, trapSensorName, trapEvent, trapSeverity, trapEventCode, trapServerIdentity, trapLocation, trapTime }
      STATUS  current
      DESCRIPTION
              "Front Panel NMI / Diagnostic Interrupt"
      ::= { ariCriticalInterrupt 1 }

    alertNMIDeassert NOTIFICATION-TYPE
      OBJECTS { trapSeq, trapSensorName, trapEvent, trapSeverity, trapEventCode, trapServerIdentity, trapLocation, trapTime }
      STATUS  current
      DESCRIPTION
              "Front Panel NMI / Diagnostic Interrupt"
      ::= { ariCriticalInterrupt 2 }

    alertBusTimeout NOTIFICATION-TYPE
      OBJECTS { trapSeq, trapSensorName, trapEvent, trapSeverity, trapEventCode, trapServerIdentity, trapLocation, trapTime }
      STATUS  current
      DESCRIPTION
              "Bus Timeout"
      ::= { ariCriticalInterrupt 17 }

    alertBusTimeoutDeassert NOTIFICATION-TYPE
      OBJECTS { trapSeq, trapSensorName, trapEvent, trapSeverity, trapEventCode, trapServerIdentity, trapLocation, trapTime }
      STATUS  current
      DESCRIPTION
              "Bus Timeout"
      ::= { ariCriticalInterrupt 18 }

    alertIOChannelCheckNMI NOTIFICATION-TYPE
      OBJECTS { trapSeq, trapSensorName, trapEvent, trapSeverity, trapEventCode, trapServerIdentity, trapLocation, trapTime }
      STATUS  current
      DESCRIPTION
              "I/O channel check NMI"
      ::= { ariCriticalInterrupt 33 }

    alertIOChannelCheckNMIDeassert NOTIFICATION-TYPE
      OBJECTS { trapSeq, trapSensorName, trapEvent, trapSeverity, trapEventCode, trapServerIdentity, trapLocation, trapTime }
      STATUS  current
      DESCRIPTION
              "I/O channel check NMI"
      ::= { ariCriticalInterrupt 34 }

    alertSoftwareNMI NOTIFICATION-TYPE
      OBJECTS { trapSeq, trapSensorName, trapEvent, trapSeverity, trapEventCode, trapServerIdentity, trapLocation, trapTime }
      STATUS  current
      DESCRIPTION
              "Software NMI"
      ::= { ariCriticalInterrupt 49 }

    alertSoftwareNMIDeassert NOTIFICATION-TYPE
      OBJECTS { trapSeq, trapSensorName, trapEvent, trapSeverity, trapEventCode, trapServerIdentity, trapLocation, trapTime }
      STATUS  current
      DESCRIPTION
              "Software NMI"
      ::= { ariCriticalInterrupt 50 }
      
    alertPCIPERR NOTIFICATION-TYPE
      OBJECTS { trapSeq, trapSensorName, trapEvent, trapSeverity, trapEventCode, trapServerIdentity, trapLocation, trapTime }
      STATUS  current
      DESCRIPTION
              "PCI PERR"
      ::= { ariCriticalInterrupt 65 }

    alertPCIPERRDeassert NOTIFICATION-TYPE
      OBJECTS { trapSeq, trapSensorName, trapEvent, trapSeverity, trapEventCode, trapServerIdentity, trapLocation, trapTime }
      STATUS  current
      DESCRIPTION
              "PCI PERR"
      ::= { ariCriticalInterrupt 66 }
      
    alertPCISERR NOTIFICATION-TYPE
      OBJECTS { trapSeq, trapSensorName, trapEvent, trapSeverity, trapEventCode, trapServerIdentity, trapLocation, trapTime }
      STATUS  current
      DESCRIPTION
              "PCI SERR"
      ::= { ariCriticalInterrupt 81 }

    alertPCISERRDeassert NOTIFICATION-TYPE
      OBJECTS { trapSeq, trapSensorName, trapEvent, trapSeverity, trapEventCode, trapServerIdentity, trapLocation, trapTime }
      STATUS  current
      DESCRIPTION
              "PCI SERR"
      ::= { ariCriticalInterrupt 82 }
      
    alertEISAFailSafeTimeout NOTIFICATION-TYPE
      OBJECTS { trapSeq, trapSensorName, trapEvent, trapSeverity, trapEventCode, trapServerIdentity, trapLocation, trapTime }
      STATUS  current
      DESCRIPTION
              "EISA Fail Safe Timeout"
      ::= { ariCriticalInterrupt 97 }

    alertEISAFailSafeTimeoutDeassert NOTIFICATION-TYPE
      OBJECTS { trapSeq, trapSensorName, trapEvent, trapSeverity, trapEventCode, trapServerIdentity, trapLocation, trapTime }
      STATUS  current
      DESCRIPTION
              "EISA Fail Safe Timeout"
      ::= { ariCriticalInterrupt 98 }
      
    alertBusCorrectableError NOTIFICATION-TYPE
      OBJECTS { trapSeq, trapSensorName, trapEvent, trapSeverity, trapEventCode, trapServerIdentity, trapLocation, trapTime }
      STATUS  current
      DESCRIPTION
              "Bus Correctable Error"
      ::= { ariCriticalInterrupt 113 }

    alertBusCorrectableErrorDeassert NOTIFICATION-TYPE
      OBJECTS { trapSeq, trapSensorName, trapEvent, trapSeverity, trapEventCode, trapServerIdentity, trapLocation, trapTime }
      STATUS  current
      DESCRIPTION
              "Bus Correctable Error"
      ::= { ariCriticalInterrupt 114 }
      
    alertBusUncorrectableError NOTIFICATION-TYPE
      OBJECTS { trapSeq, trapSensorName, trapEvent, trapSeverity, trapEventCode, trapServerIdentity, trapLocation, trapTime }
      STATUS  current
      DESCRIPTION
              "Bus Uncorrectable Error"
      ::= { ariCriticalInterrupt 129 }

    alertBusUncorrectableErrorDeassert NOTIFICATION-TYPE
      OBJECTS { trapSeq, trapSensorName, trapEvent, trapSeverity, trapEventCode, trapServerIdentity, trapLocation, trapTime }
      STATUS  current
      DESCRIPTION
              "Bus Uncorrectable Error"
      ::= { ariCriticalInterrupt 130 }
      
    alertFatalNMI NOTIFICATION-TYPE
      OBJECTS { trapSeq, trapSensorName, trapEvent, trapSeverity, trapEventCode, trapServerIdentity, trapLocation, trapTime }
      STATUS  current
      DESCRIPTION
              "Fatal NMI (port 61h, bit 7)"
      ::= { ariCriticalInterrupt 145 }

    alertFatalNMIDeassert NOTIFICATION-TYPE
      OBJECTS { trapSeq, trapSensorName, trapEvent, trapSeverity, trapEventCode, trapServerIdentity, trapLocation, trapTime }
      STATUS  current
      DESCRIPTION
              "Fatal NMI (port 61h, bit 7)"
      ::= { ariCriticalInterrupt 146 }

    alertBusFatalError NOTIFICATION-TYPE
      OBJECTS { trapSeq, trapSensorName, trapEvent, trapSeverity, trapEventCode, trapServerIdentity, trapLocation, trapTime }
      STATUS  current
      DESCRIPTION
              "Bus Fatal Error"
      ::= { ariCriticalInterrupt 161 }

    alertBusFatalErrorDeassert NOTIFICATION-TYPE
      OBJECTS { trapSeq, trapSensorName, trapEvent, trapSeverity, trapEventCode, trapServerIdentity, trapLocation, trapTime }
      STATUS  current
      DESCRIPTION
              "Bus Fatal Error"
      ::= { ariCriticalInterrupt 162 }

    alertBusDegraded NOTIFICATION-TYPE
      OBJECTS { trapSeq, trapSensorName, trapEvent, trapSeverity, trapEventCode, trapServerIdentity, trapLocation, trapTime }
      STATUS  current
      DESCRIPTION
              "Bus Degraded (bus operating in a degraded performance state)"
      ::= { ariCriticalInterrupt 177 }

    alertBusDegradedDeassert NOTIFICATION-TYPE
      OBJECTS { trapSeq, trapSensorName, trapEvent, trapSeverity, trapEventCode, trapServerIdentity, trapLocation, trapTime }
      STATUS  current
      DESCRIPTION
              "Bus Degraded (bus operating in a degraded performance state)"
      ::= { ariCriticalInterrupt 178 }

     alertStorageControllerPCIPERR NOTIFICATION-TYPE
      OBJECTS { trapSeq, trapSensorName, trapEvent, trapSeverity, trapEventCode, trapServerIdentity, trapLocation, trapTime }
      STATUS  current
      DESCRIPTION
              "Storage Controller PCI PERR"
      ::= { ariCriticalInterrupt 66625 }
 
    alertStorageControllerPCIPERRDeassert NOTIFICATION-TYPE
      OBJECTS { trapSeq, trapSensorName, trapEvent, trapSeverity, trapEventCode, trapServerIdentity, trapLocation, trapTime }
      STATUS  current
      DESCRIPTION
              "Storage Controller PCI PERR"
      ::= { ariCriticalInterrupt 66626 }
 
    alertStorageControllerPCISERR NOTIFICATION-TYPE
      OBJECTS { trapSeq, trapSensorName, trapEvent, trapSeverity, trapEventCode, trapServerIdentity, trapLocation, trapTime }
      STATUS  current
      DESCRIPTION
              "Storage Controller PCI SERR"
      ::= { ariCriticalInterrupt 66641 }
 
    alertStorageControllerPCISERRDeassert NOTIFICATION-TYPE
      OBJECTS { trapSeq, trapSensorName, trapEvent, trapSeverity, trapEventCode, trapServerIdentity, trapLocation, trapTime }
      STATUS  current
      DESCRIPTION
              "Storage Controller PCI SERR"
      ::= { ariCriticalInterrupt 66642 }
 
    alertStorageControllerBusCorrectableError NOTIFICATION-TYPE
      OBJECTS { trapSeq, trapSensorName, trapEvent, trapSeverity, trapEventCode, trapServerIdentity, trapLocation, trapTime }
      STATUS  current
      DESCRIPTION
              "Storage Controller Bus Correctable Error"
      ::= { ariCriticalInterrupt 66673 }
 
    alertStorageControllerBusCorrectableErrorDeassert NOTIFICATION-TYPE
      OBJECTS { trapSeq, trapSensorName, trapEvent, trapSeverity, trapEventCode, trapServerIdentity, trapLocation, trapTime }
      STATUS  current
      DESCRIPTION
              "Storage Controller Bus Correctable Error"
      ::= { ariCriticalInterrupt 66674 }
 
    alertStorageControllerBusUncorrectableError NOTIFICATION-TYPE
      OBJECTS { trapSeq, trapSensorName, trapEvent, trapSeverity, trapEventCode, trapServerIdentity, trapLocation, trapTime }
      STATUS  current
      DESCRIPTION
              "Storage Controller Bus Uncorrectable Error"
      ::= { ariCriticalInterrupt 66689 }
 
    alertStorageControllerBusUncorrectableErrorDeassert NOTIFICATION-TYPE
      OBJECTS { trapSeq, trapSensorName, trapEvent, trapSeverity, trapEventCode, trapServerIdentity, trapLocation, trapTime }
      STATUS  current
      DESCRIPTION
              "Storage Controller Bus Uncorrectable Error"
      ::= { ariCriticalInterrupt 66690 }
 
    alertStorageControllerBusFatalError NOTIFICATION-TYPE
      OBJECTS { trapSeq, trapSensorName, trapEvent, trapSeverity, trapEventCode, trapServerIdentity, trapLocation, trapTime }
      STATUS  current
      DESCRIPTION
              "Storage Controller Bus Fatal Error"
      ::= { ariCriticalInterrupt 66721 }
 
    alertStorageControllerBusFatalErrorDeassert NOTIFICATION-TYPE
      OBJECTS { trapSeq, trapSensorName, trapEvent, trapSeverity, trapEventCode, trapServerIdentity, trapLocation, trapTime }
      STATUS  current
      DESCRIPTION
              "Storage Controller Bus Fatal Error"
      ::= { ariCriticalInterrupt 66722 }

     alertNVMePCIPERR NOTIFICATION-TYPE
      OBJECTS { trapSeq, trapSensorName, trapEvent, trapSeverity, trapEventCode, trapServerIdentity, trapLocation, trapTime }
      STATUS  current
      DESCRIPTION
              "NVMe PCI PERR"
      ::= { ariCriticalInterrupt 67649 }
 
    alertNVMePCIPERRDeassert NOTIFICATION-TYPE
      OBJECTS { trapSeq, trapSensorName, trapEvent, trapSeverity, trapEventCode, trapServerIdentity, trapLocation, trapTime }
      STATUS  current
      DESCRIPTION
              "NVMe PCI PERR"
      ::= { ariCriticalInterrupt 67650 }
 
    alertNVMePCISERR NOTIFICATION-TYPE
      OBJECTS { trapSeq, trapSensorName, trapEvent, trapSeverity, trapEventCode, trapServerIdentity, trapLocation, trapTime }
      STATUS  current
      DESCRIPTION
              "NVMe PCI SERR"
      ::= { ariCriticalInterrupt 67665 }
 
    alertNVMePCISERRDeassert NOTIFICATION-TYPE
      OBJECTS { trapSeq, trapSensorName, trapEvent, trapSeverity, trapEventCode, trapServerIdentity, trapLocation, trapTime }
      STATUS  current
      DESCRIPTION
              "NVMe PCI SERR"
      ::= { ariCriticalInterrupt 67666 }
 
    alertNVMeBusCorrectableError NOTIFICATION-TYPE
      OBJECTS { trapSeq, trapSensorName, trapEvent, trapSeverity, trapEventCode, trapServerIdentity, trapLocation, trapTime }
      STATUS  current
      DESCRIPTION
              "NVMe Bus Correctable Error"
      ::= { ariCriticalInterrupt 67697 }
 
    alertNVMeBusCorrectableErrorDeassert NOTIFICATION-TYPE
      OBJECTS { trapSeq, trapSensorName, trapEvent, trapSeverity, trapEventCode, trapServerIdentity, trapLocation, trapTime }
      STATUS  current
      DESCRIPTION
              "NVMe Bus Correctable Error"
      ::= { ariCriticalInterrupt 67698 }
 
    alertNVMeBusUncorrectableError NOTIFICATION-TYPE
      OBJECTS { trapSeq, trapSensorName, trapEvent, trapSeverity, trapEventCode, trapServerIdentity, trapLocation, trapTime }
      STATUS  current
      DESCRIPTION
              "NVMe Bus Uncorrectable Error"
      ::= { ariCriticalInterrupt 67713 }
 
    alertNVMeBusUncorrectableErrorDeassert NOTIFICATION-TYPE
      OBJECTS { trapSeq, trapSensorName, trapEvent, trapSeverity, trapEventCode, trapServerIdentity, trapLocation, trapTime }
      STATUS  current
      DESCRIPTION
              "NVMe Bus Uncorrectable Error"
      ::= { ariCriticalInterrupt 67714 }
 
    alertNVMeBusFatalError NOTIFICATION-TYPE
      OBJECTS { trapSeq, trapSensorName, trapEvent, trapSeverity, trapEventCode, trapServerIdentity, trapLocation, trapTime }
      STATUS  current
      DESCRIPTION
              "NVMe Bus Fatal Error"
      ::= { ariCriticalInterrupt 67745 }
 
    alertNVMeBusFatalErrorDeassert NOTIFICATION-TYPE
      OBJECTS { trapSeq, trapSensorName, trapEvent, trapSeverity, trapEventCode, trapServerIdentity, trapLocation, trapTime }
      STATUS  current
      DESCRIPTION
              "NVMe Bus Fatal Error"
      ::= { ariCriticalInterrupt 67746 }

    alertNICPCIPERR NOTIFICATION-TYPE
      OBJECTS { trapSeq, trapSensorName, trapEvent, trapSeverity, trapEventCode, trapServerIdentity, trapLocation, trapTime }
      STATUS  current
      DESCRIPTION
              "Network Controller PCI PERR"
      ::= { ariCriticalInterrupt 131137 }
 
    alertNICPCIPERRDeassert NOTIFICATION-TYPE
      OBJECTS { trapSeq, trapSensorName, trapEvent, trapSeverity, trapEventCode, trapServerIdentity, trapLocation, trapTime }
      STATUS  current
      DESCRIPTION
              "Network Controller PCI PERR"
      ::= { ariCriticalInterrupt 131138 }
 
    alertNICPCISERR NOTIFICATION-TYPE
      OBJECTS { trapSeq, trapSensorName, trapEvent, trapSeverity, trapEventCode, trapServerIdentity, trapLocation, trapTime }
      STATUS  current
      DESCRIPTION
              "Network Controller PCI SERR"
      ::= { ariCriticalInterrupt 131153 }
 
    alertNICPCISERRDeassert NOTIFICATION-TYPE
      OBJECTS { trapSeq, trapSensorName, trapEvent, trapSeverity, trapEventCode, trapServerIdentity, trapLocation, trapTime }
      STATUS  current
      DESCRIPTION
              "Network Controller PCI SERR"
      ::= { ariCriticalInterrupt 131154 }
 
    alertNICBusCorrectableError NOTIFICATION-TYPE
      OBJECTS { trapSeq, trapSensorName, trapEvent, trapSeverity, trapEventCode, trapServerIdentity, trapLocation, trapTime }
      STATUS  current
      DESCRIPTION
              "Network Controller Bus Correctable Error"
      ::= { ariCriticalInterrupt 131185 }
 
    alertNICBusCorrectableErrorDeassert NOTIFICATION-TYPE
      OBJECTS { trapSeq, trapSensorName, trapEvent, trapSeverity, trapEventCode, trapServerIdentity, trapLocation, trapTime }
      STATUS  current
      DESCRIPTION
              "Network Controller Bus Correctable Error"
      ::= { ariCriticalInterrupt 131186 }
 
    alertNICBusUncorrectableError NOTIFICATION-TYPE
      OBJECTS { trapSeq, trapSensorName, trapEvent, trapSeverity, trapEventCode, trapServerIdentity, trapLocation, trapTime }
      STATUS  current
      DESCRIPTION
              "Network Controller Bus Uncorrectable Error"
      ::= { ariCriticalInterrupt 131201 }
 
    alertNICBusUncorrectableErrorDeassert NOTIFICATION-TYPE
      OBJECTS { trapSeq, trapSensorName, trapEvent, trapSeverity, trapEventCode, trapServerIdentity, trapLocation, trapTime }
      STATUS  current
      DESCRIPTION
              "Network Controller Bus Uncorrectable Error"
      ::= { ariCriticalInterrupt 131202 }
 
    alertNICBusFatalError NOTIFICATION-TYPE
      OBJECTS { trapSeq, trapSensorName, trapEvent, trapSeverity, trapEventCode, trapServerIdentity, trapLocation, trapTime }
      STATUS  current
      DESCRIPTION
              "Network Controller Bus Fatal Error"
      ::= { ariCriticalInterrupt 131233 }
 
    alertNICBusFatalErrorDeassert NOTIFICATION-TYPE
      OBJECTS { trapSeq, trapSensorName, trapEvent, trapSeverity, trapEventCode, trapServerIdentity, trapLocation, trapTime }
      STATUS  current
      DESCRIPTION
              "Network Controller Bus Fatal Error"
      ::= { ariCriticalInterrupt 131234 }
  
    ariPowerButton OBJECT IDENTIFIER ::= {serverAlertTrapGroup 20}                         

    alertPowerButtonPressed NOTIFICATION-TYPE
      OBJECTS { trapSeq, trapSensorName, trapEvent, trapSeverity, trapEventCode, trapServerIdentity, trapLocation, trapTime }
      STATUS  current
      DESCRIPTION
              "Power button pressed"
      ::= { ariPowerButton 1 }

    alertPowerButtonReleased NOTIFICATION-TYPE
      OBJECTS { trapSeq, trapSensorName, trapEvent, trapSeverity, trapEventCode, trapServerIdentity, trapLocation, trapTime }
      STATUS  current
      DESCRIPTION
              "Power button released "
      ::= { ariPowerButton 2 }
  
    ariCable OBJECT IDENTIFIER ::= {serverAlertTrapGroup 27}
    
    alertLANCableStatus NOTIFICATION-TYPE
      OBJECTS { trapSeq, trapSensorName, trapEvent, trapSeverity, trapEventCode, trapServerIdentity, trapLocation, trapTime }
      STATUS  current
      DESCRIPTION
              "Cable/Interconnect is connected"
      ::= { ariCable 1 }
      
     alertLANCableStatusDeassert NOTIFICATION-TYPE
      OBJECTS { trapSeq, trapSensorName, trapEvent, trapSeverity, trapEventCode, trapServerIdentity, trapLocation, trapTime }
      STATUS  current
      DESCRIPTION
              "Cable/Interconnect is connected deassert"
      ::= { ariCable 2 }
    
    alertCableStatus NOTIFICATION-TYPE
      OBJECTS { trapSeq, trapSensorName, trapEvent, trapSeverity, trapEventCode, trapServerIdentity, trapLocation, trapTime }
      STATUS  current
      DESCRIPTION
              "SAS or Harddisk backplane cable config error"
      ::= { ariCable 17 }

    alertCableStatusDeassert NOTIFICATION-TYPE
      OBJECTS { trapSeq, trapSensorName, trapEvent, trapSeverity, trapEventCode, trapServerIdentity, trapLocation, trapTime }
      STATUS  current
      DESCRIPTION
              "SAS or Harddisk backplane cable config error deassert"
      ::= { ariCable 18 }


  
    ariSysRestart OBJECT IDENTIFIER ::= {serverAlertTrapGroup 29}
    
    alertSysRestartUnknownAsserted NOTIFICATION-TYPE
      OBJECTS { trapSeq, trapSensorName, trapEvent, trapSeverity, trapEventCode, trapServerIdentity, trapLocation, trapTime }
      STATUS  current
      DESCRIPTION
              "system restart unknown asserted"
      ::= { ariSysRestart 113 }

    alertSysRestartUnknownDeasserted NOTIFICATION-TYPE
      OBJECTS { trapSeq, trapSensorName, trapEvent, trapSeverity, trapEventCode, trapServerIdentity, trapLocation, trapTime }
      STATUS  current
      DESCRIPTION
              "system restart unknown deasserted"
      ::= { ariSysRestart 114 }

    alertSysRestartChassisCtrlAsserted NOTIFICATION-TYPE
      OBJECTS { trapSeq, trapSensorName, trapEvent, trapSeverity, trapEventCode, trapServerIdentity, trapLocation, trapTime }
      STATUS  current
      DESCRIPTION
              "system restart Chassis Control command asserted"
      ::= { ariSysRestart 369 }

    alertSysRestartChassisCtrlDeasserted NOTIFICATION-TYPE
      OBJECTS { trapSeq, trapSensorName, trapEvent, trapSeverity, trapEventCode, trapServerIdentity, trapLocation, trapTime }
      STATUS  current
      DESCRIPTION
              "system restart Chassis Control command deasserted"
      ::= { ariSysRestart 370 }

    alertSysRestartButtonAsserted NOTIFICATION-TYPE
      OBJECTS { trapSeq, trapSensorName, trapEvent, trapSeverity, trapEventCode, trapServerIdentity, trapLocation, trapTime }
      STATUS  current
      DESCRIPTION
              "System Restart reset via pushbutton asserted"
      ::= { ariSysRestart 625 }

    alertSysRestartButtonDeasserted NOTIFICATION-TYPE
      OBJECTS { trapSeq, trapSensorName, trapEvent, trapSeverity, trapEventCode, trapServerIdentity, trapLocation, trapTime }
      STATUS  current
      DESCRIPTION
              "System Restart reset via pushbutton deasserted"
      ::= { ariSysRestart 626 }

    alertSysRestartPowerButton NOTIFICATION-TYPE
      OBJECTS { trapSeq, trapSensorName, trapEvent, trapSeverity, trapEventCode, trapServerIdentity, trapLocation, trapTime }
      STATUS  current
      DESCRIPTION
              "system restart cause power button pressed"
      ::= { ariSysRestart 881 }


    alertSysRestartWatchdogCtrl NOTIFICATION-TYPE
      OBJECTS { trapSeq, trapSensorName, trapEvent, trapSeverity, trapEventCode, trapServerIdentity, trapLocation, trapTime }
      STATUS  current
      DESCRIPTION
              "system restart cause Watchdog control"
      ::= { ariSysRestart 1137 }
      
    alertSysRestartAlwaysRestore NOTIFICATION-TYPE
      OBJECTS { trapSeq, trapSensorName, trapEvent, trapSeverity, trapEventCode, trapServerIdentity, trapLocation, trapTime }
      STATUS  current
      DESCRIPTION
              "system restart cause always power up"
      ::= { ariSysRestart 1649 }

    alertSysRestartRestorePrevState NOTIFICATION-TYPE
      OBJECTS { trapSeq, trapSensorName, trapEvent, trapSeverity, trapEventCode, trapServerIdentity, trapLocation, trapTime }
      STATUS  current
      DESCRIPTION
              "system restart cause always restore previous state"
      ::= { ariSysRestart 1905 }
  
    alertSysRestartSoftAsserted NOTIFICATION-TYPE
      OBJECTS { trapSeq, trapSensorName, trapEvent, trapSeverity, trapEventCode, trapServerIdentity, trapLocation, trapTime }
      STATUS  current
      DESCRIPTION
              "System Restart via soft reset asserted"
      ::= { ariSysRestart 2673 }

    alertSysRestartSoftDeasserted NOTIFICATION-TYPE
      OBJECTS { trapSeq, trapSensorName, trapEvent, trapSeverity, trapEventCode, trapServerIdentity, trapLocation, trapTime }
      STATUS  current
      DESCRIPTION
              "System Restart via soft reset deasserted"
      ::= { ariSysRestart 2674 }  

    ariBootError OBJECT IDENTIFIER ::= {serverAlertTrapGroup 30}
    
    alertNoBootableMedia NOTIFICATION-TYPE
      OBJECTS { trapSeq, trapSensorName, trapEvent, trapSeverity, trapEventCode, trapServerIdentity, trapLocation, trapTime }
      STATUS  current
      DESCRIPTION
              "boot error, no bootable media"
      ::= { ariBootError 1 }

    alertNoBootableMediaDeassert NOTIFICATION-TYPE
      OBJECTS { trapSeq, trapSensorName, trapEvent, trapSeverity, trapEventCode, trapServerIdentity, trapLocation, trapTime }
      STATUS  current
      DESCRIPTION
              "boot error, no bootable media deassert"
      ::= { ariBootError 2 }

    alertNoBootableDisk NOTIFICATION-TYPE
      OBJECTS { trapSeq, trapSensorName, trapEvent, trapSeverity, trapEventCode, trapServerIdentity, trapLocation, trapTime }
      STATUS  current
      DESCRIPTION
              "boot error, Non-bootable disk in drive"
      ::= { ariBootError 17 }

    alertNoBootableDiskDeassert NOTIFICATION-TYPE
      OBJECTS { trapSeq, trapSensorName, trapEvent, trapSeverity, trapEventCode, trapServerIdentity, trapLocation, trapTime }
      STATUS  current
      DESCRIPTION
              "boot error, Non-bootable disk in drive deassert"
      ::= { ariBootError 18 }

    alertPXENotFound NOTIFICATION-TYPE
      OBJECTS { trapSeq, trapSensorName, trapEvent, trapSeverity, trapEventCode, trapServerIdentity, trapLocation, trapTime }
      STATUS  current
      DESCRIPTION
              "boot error, PXE server not found"
      ::= { ariBootError 33 }

    alertPXENotFoundDeassert NOTIFICATION-TYPE
      OBJECTS { trapSeq, trapSensorName, trapEvent, trapSeverity, trapEventCode, trapServerIdentity, trapLocation, trapTime }
      STATUS  current
      DESCRIPTION
              "boot error, PXE server not found deassert"
      ::= { ariBootError 34 }


    alertInvalidBootSector NOTIFICATION-TYPE
      OBJECTS { trapSeq, trapSensorName, trapEvent, trapSeverity, trapEventCode, trapServerIdentity, trapLocation, trapTime }
      STATUS  current
      DESCRIPTION
              "boot error, Invalid boot sector"
      ::= { ariBootError 49 }

    alertInvalidBootSectorDeassert NOTIFICATION-TYPE
      OBJECTS { trapSeq, trapSensorName, trapEvent, trapSeverity, trapEventCode, trapServerIdentity, trapLocation, trapTime }
      STATUS  current
      DESCRIPTION
              "boot error, Invalid boot sector deassert"
      ::= { ariBootError 50 }

  
  
    ariDeviceFault OBJECT IDENTIFIER ::= {serverAlertTrapGroup 33}
    
    
    alertHardwareAddrFault NOTIFICATION-TYPE
      OBJECTS { trapSeq, trapSensorName, trapEvent, trapSeverity, trapEventCode, trapServerIdentity, trapLocation, trapTime }
      STATUS  current
      DESCRIPTION
              "Hardware address in fault status"
      ::= { ariDeviceFault 1 }


    alertHardwareAddrFaultDeassert NOTIFICATION-TYPE
      OBJECTS { trapSeq, trapSensorName, trapEvent, trapSeverity, trapEventCode, trapServerIdentity, trapLocation, trapTime }
      STATUS  current
      DESCRIPTION
              "Hardware address in fault status deassert"
      ::= { ariDeviceFault 2 }

    alertDeviceInstall NOTIFICATION-TYPE
      OBJECTS { trapSeq, trapSensorName, trapEvent, trapSeverity, trapEventCode, trapServerIdentity, trapLocation, trapTime }
      STATUS  current
      DESCRIPTION
              "Device installed"
      ::= { ariDeviceFault 33 }


    alertDeviceInstallDeassert NOTIFICATION-TYPE
      OBJECTS { trapSeq, trapSensorName, trapEvent, trapSeverity, trapEventCode, trapServerIdentity, trapLocation, trapTime }
      STATUS  current
      DESCRIPTION
              "Device installed deassert"
      ::= { ariDeviceFault 34 }   
     
    alertEthLinkDown NOTIFICATION-TYPE
      OBJECTS { trapSeq, trapSensorName, trapEvent, trapSeverity, trapEventCode, trapServerIdentity, trapLocation, trapTime }
      STATUS  current
      DESCRIPTION
              "System Eth link down"
      ::= { ariDeviceFault 129 }


    alertEthLinkDownDeassert NOTIFICATION-TYPE
      OBJECTS { trapSeq, trapSensorName, trapEvent, trapSeverity, trapEventCode, trapServerIdentity, trapLocation, trapTime }
      STATUS  current
      DESCRIPTION
              "System Eth link down deassert"
      ::= { ariDeviceFault 130 } 
      
      
  alertMemBrdMigrate NOTIFICATION-TYPE
      OBJECTS { trapSeq, trapSensorName, trapEvent, trapSeverity, trapEventCode, trapServerIdentity, trapLocation, trapTime }
      STATUS  current
      DESCRIPTION
              "Spare Device"
      ::= { ariDeviceFault 145 } 
    
  alertMemBrdMigrateDeassert NOTIFICATION-TYPE
      OBJECTS { trapSeq, trapSensorName, trapEvent, trapSeverity, trapEventCode, trapServerIdentity, trapLocation, trapTime }
      STATUS  current
      DESCRIPTION
              "Spare Device deassert"
      ::= { ariDeviceFault 146 } 
    
  alertPCIEStatus NOTIFICATION-TYPE
      OBJECTS { trapSeq, trapSensorName, trapEvent, trapSeverity, trapEventCode, trapServerIdentity, trapLocation, trapTime }
      STATUS  current
      DESCRIPTION
              "PCIe Error"
      ::= { ariDeviceFault 257 } 
    
  alertPCIEStatusDeassert NOTIFICATION-TYPE
      OBJECTS { trapSeq, trapSensorName, trapEvent, trapSeverity, trapEventCode, trapServerIdentity, trapLocation, trapTime }
      STATUS  current
      DESCRIPTION
              "PCIe Error deassert"
      ::= { ariDeviceFault 258 } 
      
    alertFanFault NOTIFICATION-TYPE
      OBJECTS { trapSeq, trapSensorName, trapEvent, trapSeverity, trapEventCode, trapServerIdentity, trapLocation, trapTime }
      STATUS  current
      DESCRIPTION
              "fan in fault status"
      ::= { ariDeviceFault 2049 }

    alertFanFaultDeassert NOTIFICATION-TYPE
      OBJECTS { trapSeq, trapSensorName, trapEvent, trapSeverity, trapEventCode, trapServerIdentity, trapLocation, trapTime }
      STATUS  current
      DESCRIPTION
              "fan in fault status deassert"
      ::= { ariDeviceFault 2050 }

    alertPCIeFault NOTIFICATION-TYPE
      OBJECTS { trapSeq, trapSensorName, trapEvent, trapSeverity, trapEventCode, trapEventData2, trapEventData3, trapServerIdentity, trapLocation, trapTime }
      STATUS  current
      DESCRIPTION
              "PCIe in fault status"
      ::= { ariDeviceFault 2305 }

    alertPCIeFaultDeassert NOTIFICATION-TYPE
      OBJECTS { trapSeq, trapSensorName, trapEvent, trapSeverity, trapEventCode, trapEventData2, trapEventData3, trapServerIdentity, trapLocation, trapTime }
      STATUS  current
      DESCRIPTION
              "PCIe in fault status deassert"
      ::= { ariDeviceFault 2306 } 



  
    ariACPIStatus OBJECT IDENTIFIER ::= {serverAlertTrapGroup 34}                         
    
    alertACPIStatusS0G0 NOTIFICATION-TYPE
      OBJECTS { trapSeq, trapSensorName, trapEvent, trapSeverity, trapEventCode, trapServerIdentity, trapLocation, trapTime }
      STATUS  current
      DESCRIPTION
              "ACPI status S0/G0 working"
      ::= { ariACPIStatus 1 }

    alertACPIStatusS4S5 NOTIFICATION-TYPE
      OBJECTS { trapSeq, trapSensorName, trapEvent, trapSeverity, trapEventCode, trapServerIdentity, trapLocation, trapTime }
      STATUS  current
      DESCRIPTION
              "ACPI status, S4/S5 soft-off, particular when S4/S5 state cannot be determined"
      ::= { ariACPIStatus 97 }

  
    ariWatchDog2 OBJECT IDENTIFIER ::= {serverAlertTrapGroup 35}
    
    alertWatchDog2Expired NOTIFICATION-TYPE
      OBJECTS { trapSeq, trapSensorName, trapEvent, trapSeverity, trapEventCode, trapServerIdentity, trapLocation, trapTime }
      STATUS  current
      DESCRIPTION
              "watchdog2 timer expired, no action"
      ::= { ariWatchDog2 1 }

     alertWatchDogExpiredDeassert NOTIFICATION-TYPE
      OBJECTS { trapSeq, trapSensorName, trapEvent, trapSeverity, trapEventCode, trapServerIdentity, trapLocation, trapTime }
      STATUS  current
      DESCRIPTION
              "watchdog2 timer expired, no action deassert"
      ::= { ariWatchDog2 2 }
      
     alertWatchDogReset NOTIFICATION-TYPE
      OBJECTS { trapSeq, trapSensorName, trapEvent, trapSeverity, trapEventCode, trapServerIdentity, trapLocation, trapTime }
      STATUS  current
      DESCRIPTION
              "watchdog2 timer expired, hard reset"
      ::= { ariWatchDog2 17 }

     alertWatchDogResetDeassert NOTIFICATION-TYPE
      OBJECTS { trapSeq, trapSensorName, trapEvent, trapSeverity, trapEventCode, trapServerIdentity, trapLocation, trapTime }
      STATUS  current
      DESCRIPTION
              "watchdog2 timer expired, hard reset deassert"
      ::= { ariWatchDog2 18 }

     alertWatchDogPowerDown NOTIFICATION-TYPE
      OBJECTS { trapSeq, trapSensorName, trapEvent, trapSeverity, trapEventCode, trapServerIdentity, trapLocation, trapTime }
      STATUS  current
      DESCRIPTION
              "watchdog2 timer expired, power down"
      ::= { ariWatchDog2 33 }

     alertWatchDogPowerDownDeassert NOTIFICATION-TYPE
      OBJECTS { trapSeq, trapSensorName, trapEvent, trapSeverity, trapEventCode, trapServerIdentity, trapLocation, trapTime }
      STATUS  current
      DESCRIPTION
              "watchdog2 timer expired, power down deassert"
      ::= { ariWatchDog2 34 }

     alertWatchDogPowerCycle NOTIFICATION-TYPE
      OBJECTS { trapSeq, trapSensorName, trapEvent, trapSeverity, trapEventCode, trapServerIdentity, trapLocation, trapTime }
      STATUS  current
      DESCRIPTION
              "watchdog2 timer expired, power cycle"
      ::= { ariWatchDog2 49 }

     alertWatchDogPowerCycleDeassert NOTIFICATION-TYPE
      OBJECTS { trapSeq, trapSensorName, trapEvent, trapSeverity, trapEventCode, trapServerIdentity, trapLocation, trapTime }
      STATUS  current
      DESCRIPTION
              "watchdog2 timer expired, power cycle deassert"
      ::= { ariWatchDog2 50 }

  
    ariLANHeartBeat OBJECT IDENTIFIER ::= {serverAlertTrapGroup 39}
    
    alertLANHeartLost NOTIFICATION-TYPE
      OBJECTS { trapSeq, trapSensorName, trapEvent, trapSeverity, trapEventCode, trapServerIdentity, trapLocation, trapTime }
      STATUS  current
      DESCRIPTION
              "LAN heart beat lost"
      ::= { ariLANHeartBeat 1 }

    alertLANHeartLostDeassert NOTIFICATION-TYPE
      OBJECTS { trapSeq, trapSensorName, trapEvent, trapSeverity, trapEventCode, trapServerIdentity, trapLocation, trapTime }
      STATUS  current
      DESCRIPTION
              "LAN heart beat lost deassert"
      ::= { ariLANHeartBeat 2 }

  
    ariMngmntHealth OBJECT IDENTIFIER ::= {serverAlertTrapGroup 40}
    
    alertSensorAccessibleFail NOTIFICATION-TYPE
      OBJECTS { trapSeq, trapSensorName, trapEvent, trapSeverity, trapEventCode, trapServerIdentity, trapLocation, trapTime }
      STATUS  current
      DESCRIPTION
              "Sensor access degraded or unavailable"
      ::= { ariMngmntHealth 1 } 

    alertSensorAccessibleFailDeassert NOTIFICATION-TYPE
      OBJECTS { trapSeq, trapSensorName, trapEvent, trapSeverity, trapEventCode, trapServerIdentity, trapLocation, trapTime }
      STATUS  current
      DESCRIPTION
              "Sensor access degraded or unavailable deassert"
      ::= { ariMngmntHealth 2 }

    alertControllerAccessibleFail NOTIFICATION-TYPE
      OBJECTS { trapSeq, trapSensorName, trapEvent, trapSeverity, trapEventCode, trapServerIdentity, trapLocation, trapTime }
      STATUS  current
      DESCRIPTION
              "Controller access degraded or unavailable"
      ::= { ariMngmntHealth 17 } 

    alertControllerAccessibleFailDeassert NOTIFICATION-TYPE
      OBJECTS { trapSeq, trapSensorName, trapEvent, trapSeverity, trapEventCode, trapServerIdentity, trapLocation, trapTime }
      STATUS  current
      DESCRIPTION
              "Controller access degraded or unavailable deassert"
      ::= { ariMngmntHealth 18 }

    alertFruFail NOTIFICATION-TYPE
      OBJECTS { trapSeq, trapSensorName, trapEvent, trapSeverity, trapEventCode, trapServerIdentity, trapLocation, trapTime }
      STATUS  current
      DESCRIPTION
              "FRU failure"
      ::= { ariMngmntHealth 81 } 

    alertFruFailDeassert NOTIFICATION-TYPE
      OBJECTS { trapSeq, trapSensorName, trapEvent, trapSeverity, trapEventCode, trapServerIdentity, trapLocation, trapTime }
      STATUS  current
      DESCRIPTION
              "FRU failure deassert"
      ::= { ariMngmntHealth 82 }

  
    ariBattery OBJECT IDENTIFIER ::= {serverAlertTrapGroup 41} 
    
    alertRTCBatterylow NOTIFICATION-TYPE
      OBJECTS { trapSeq, trapSensorName, trapEvent, trapSeverity, trapEventCode, trapServerIdentity, trapLocation, trapTime }
      STATUS  current
      DESCRIPTION
              "RTC battery low"
      ::= { ariBattery 1 }

    alertRTCBatterylowDeassert NOTIFICATION-TYPE
      OBJECTS { trapSeq, trapSensorName, trapEvent, trapSeverity, trapEventCode, trapServerIdentity, trapLocation, trapTime }
      STATUS  current
      DESCRIPTION
              "RTC batterylow deassert"
      ::= { ariBattery 2 }

    ariVerChange OBJECT IDENTIFIER ::= {serverAlertTrapGroup 43} 
    
    alertHardwareChange NOTIFICATION-TYPE
      OBJECTS { trapSeq, trapSensorName, trapEvent, trapSeverity, trapEventCode, trapServerIdentity, trapLocation, trapTime }
      STATUS  current
      DESCRIPTION
              "Hardware change detected with associated Entity"
      ::= { ariVerChange 1 }

    alertFirmwareChange NOTIFICATION-TYPE
      OBJECTS { trapSeq, trapSensorName, trapEvent, trapSeverity, trapEventCode, trapServerIdentity, trapLocation, trapTime }
      STATUS  current
      DESCRIPTION
              "Firmware or software change detected with associated Entity"
      ::= { ariVerChange 17 }
    

  
    ariHotSwap OBJECT IDENTIFIER ::= {serverAlertTrapGroup 240}
    
    alertHotSwaptoM0 NOTIFICATION-TYPE
      OBJECTS { trapSeq, trapSensorName, trapEvent, trapSeverity, trapEventCode, trapServerIdentity, trapLocation, trapTime }
      STATUS  current
      DESCRIPTION
              "fru hot swap to M0 status"
      ::= { ariHotSwap 1 }

    alertHotSwaptoM1 NOTIFICATION-TYPE
      OBJECTS { trapSeq, trapSensorName, trapEvent, trapSeverity, trapEventCode, trapServerIdentity, trapLocation, trapTime }
      STATUS  current
      DESCRIPTION
              "fru hot swap to M1 status"
      ::= { ariHotSwap 17 }

    alertHotSwaptoM2 NOTIFICATION-TYPE
      OBJECTS { trapSeq, trapSensorName, trapEvent, trapSeverity, trapEventCode, trapServerIdentity, trapLocation, trapTime }
      STATUS  current
      DESCRIPTION
              "fru hot swap to M2 status"
      ::= { ariHotSwap 33 }

    alertHotSwaptoM3 NOTIFICATION-TYPE
      OBJECTS { trapSeq, trapSensorName, trapEvent, trapSeverity, trapEventCode, trapServerIdentity, trapLocation, trapTime }
      STATUS  current
      DESCRIPTION
              "fru hot swap to M3 status"
      ::= { ariHotSwap 49 }

    alertHotSwaptoM4 NOTIFICATION-TYPE
      OBJECTS { trapSeq, trapSensorName, trapEvent, trapSeverity, trapEventCode, trapServerIdentity, trapLocation, trapTime }
      STATUS  current
      DESCRIPTION
              "fru hot swap to M4 status"
      ::= { ariHotSwap 65 }

    alertHotSwaptoM5 NOTIFICATION-TYPE
      OBJECTS { trapSeq, trapSensorName, trapEvent, trapSeverity, trapEventCode, trapServerIdentity, trapLocation, trapTime }
      STATUS  current
      DESCRIPTION
              "fru hot swap to M5 status"
      ::= { ariHotSwap 81 }

    alertHotSwaptoM6 NOTIFICATION-TYPE
      OBJECTS { trapSeq, trapSensorName, trapEvent, trapSeverity, trapEventCode, trapServerIdentity, trapLocation, trapTime }
      STATUS  current
      DESCRIPTION
              "fru hot swap to M6 status"
      ::= { ariHotSwap 97 }

    alertHotSwaptoM7 NOTIFICATION-TYPE
      OBJECTS { trapSeq, trapSensorName, trapEvent, trapSeverity, trapEventCode, trapServerIdentity, trapLocation, trapTime }
      STATUS  current
      DESCRIPTION
              "fru hot swap to M7 status"
      ::= { ariHotSwap 113 }

  
    ariIPMBLink OBJECT IDENTIFIER ::= {serverAlertTrapGroup 241}
    
    alertIPMBLinkStateAll NOTIFICATION-TYPE
      OBJECTS { trapSeq, trapSensorName, trapEvent, trapSeverity, trapEventCode, trapServerIdentity, trapLocation, trapTime }
      STATUS  current
      DESCRIPTION
              "IPMB-A disabled. IPMB-B disabled"
      ::= { ariIPMBLink 1 }

    alertIPMBLinkStateAllDeassert NOTIFICATION-TYPE
      OBJECTS { trapSeq, trapSensorName, trapEvent, trapSeverity, trapEventCode, trapServerIdentity, trapLocation, trapTime }
      STATUS  current
      DESCRIPTION
              "IPMB-A disabled. IPMB-B disabled deassert"
      ::= { ariIPMBLink 2 }
      
    alertIPMBLinkStateB NOTIFICATION-TYPE
      OBJECTS { trapSeq, trapSensorName, trapEvent, trapSeverity, trapEventCode, trapServerIdentity, trapLocation, trapTime }
      STATUS  current
      DESCRIPTION
              "IPMB-A enabled.IPMB-B disabled"
      ::= { ariIPMBLink 17 }

    alertIPMBLinkStateBDeassert NOTIFICATION-TYPE
      OBJECTS { trapSeq, trapSensorName, trapEvent, trapSeverity, trapEventCode, trapServerIdentity, trapLocation, trapTime }
      STATUS  current
      DESCRIPTION
              "IPMB-A enabled.IPMB-B disabled deassert"
      ::= { ariIPMBLink 18 }

    alertIPMBLinkStateA NOTIFICATION-TYPE
      OBJECTS { trapSeq, trapSensorName, trapEvent, trapSeverity, trapEventCode, trapServerIdentity, trapLocation, trapTime }
      STATUS  current
      DESCRIPTION
              "IPMB-A disabled.IPMB-B enabled"
      ::= { ariIPMBLink 33 }

    alertIPMBLinkStateADeassert NOTIFICATION-TYPE
      OBJECTS { trapSeq, trapSensorName, trapEvent, trapSeverity, trapEventCode, trapServerIdentity, trapLocation, trapTime }
      STATUS  current
      DESCRIPTION
              "IPMB-A disabled.IPMB-B enabled deassert"
      ::= { ariIPMBLink 34 }

    alertIPMBLinkStateNoFault NOTIFICATION-TYPE
      OBJECTS { trapSeq, trapSensorName, trapEvent, trapSeverity, trapEventCode, trapServerIdentity, trapLocation, trapTime }
      STATUS  current
      DESCRIPTION
              "IPMB bus no fault"
      ::= { ariIPMBLink 49 }
      
  
    ariTrapTest OBJECT IDENTIFIER ::= {serverAlertTrapGroup 256}                         
    alertTrapTestInstance NOTIFICATION-TYPE
      OBJECTS { trapSeq, trapSensorName, trapEvent, trapSeverity, trapEventCode, trapServerIdentity, trapLocation, trapTime }
      STATUS  current
      DESCRIPTION
              "trap test"
      ::= { ariTrapTest 1 }
      
    ariOvertemperature OBJECT IDENTIFIER ::= {serverAlertTrapGroup 257}
                             
    alertOvertempMinor NOTIFICATION-TYPE
      OBJECTS { trapSeq, trapSensorName, trapEvent, trapSeverity, trapEventCode, trapServerIdentity, trapLocation, trapTime }
      STATUS  current
      DESCRIPTION
              "temperature above minor threshold"
      ::= { ariOvertemperature 113 }  
      
     alertOvertempMinorDeassert NOTIFICATION-TYPE
      OBJECTS { trapSeq, trapSensorName, trapEvent, trapSeverity, trapEventCode, trapServerIdentity, trapLocation, trapTime }
      STATUS  current
      DESCRIPTION
              "temperature above minor threshold deassert"
      ::= { ariOvertemperature 114 }  
      
     alertOvertempMajor NOTIFICATION-TYPE
      OBJECTS { trapSeq, trapSensorName, trapEvent, trapSeverity, trapEventCode, trapServerIdentity, trapLocation, trapTime }
      STATUS  current
      DESCRIPTION
              "temperature above major threshold"
      ::= { ariOvertemperature 145 }  
      
     alertOvertempMajorDeassert NOTIFICATION-TYPE
      OBJECTS { trapSeq, trapSensorName, trapEvent, trapSeverity, trapEventCode, trapServerIdentity, trapLocation, trapTime }
      STATUS  current
      DESCRIPTION
              "temperature above major threshold deassert"
      ::= { ariOvertemperature 146 }  
      
     alertOvertempCritical NOTIFICATION-TYPE
      OBJECTS { trapSeq, trapSensorName, trapEvent, trapSeverity, trapEventCode, trapServerIdentity, trapLocation, trapTime }
      STATUS  current
      DESCRIPTION
              "temperature above critical threshold"
      ::= { ariOvertemperature 177 }  
      
     alertOvertempCriticalDeassert NOTIFICATION-TYPE
      OBJECTS { trapSeq, trapSensorName, trapEvent, trapSeverity, trapEventCode, trapServerIdentity, trapLocation, trapTime }
      STATUS  current
      DESCRIPTION
              "temperature above critical threshold deassert"
      ::= { ariOvertemperature 178 }


    ariCPUProchot OBJECT IDENTIFIER ::= {serverAlertTrapGroup 775}  

    alertCPUProchotState NOTIFICATION-TYPE
      OBJECTS { trapSeq, trapSensorName, trapEvent, trapSeverity, trapEventCode, trapServerIdentity, trapLocation, trapTime }
      STATUS  current
      DESCRIPTION
              "CPU Prochot state asserted"
      ::= { ariCPUProchot 17 }  
      
    alertCPUProchotStateDeassert NOTIFICATION-TYPE
      OBJECTS { trapSeq, trapSensorName, trapEvent, trapSeverity, trapEventCode, trapServerIdentity, trapLocation, trapTime }
      STATUS  current
      DESCRIPTION
              "CPU Prochot state deasserted"
      ::= { ariCPUProchot 18 }  



    ariNoSDCard OBJECT IDENTIFIER ::= {serverAlertTrapGroup 781}  
    
    alertNoSDCardAssert NOTIFICATION-TYPE
      OBJECTS { trapSeq, trapSensorName, trapEvent, trapSeverity, trapEventCode, trapServerIdentity, trapLocation, trapTime }
      STATUS  current
      DESCRIPTION
              "No SD Card Assert"
      ::= { ariNoSDCard 17 }
    
    alertNoSDCardDeassert NOTIFICATION-TYPE
      OBJECTS { trapSeq, trapSensorName, trapEvent, trapSeverity, trapEventCode, trapServerIdentity, trapLocation, trapTime }
      STATUS  current
      DESCRIPTION
              "No SD Card Deassert"
      ::= { ariNoSDCard 18 }
  
    ariAddInCard OBJECT IDENTIFIER ::= {serverAlertTrapGroup 791}  
    
    alertPCIeError NOTIFICATION-TYPE
      OBJECTS { trapSeq, trapSensorName, trapEvent, trapSeverity, trapEventCode, trapServerIdentity, trapLocation, trapTime }
      STATUS  current
      DESCRIPTION
              "PCIe Error"
      ::= { ariAddInCard 17 }
    
    alertPCIeErrorDeassert NOTIFICATION-TYPE
      OBJECTS { trapSeq, trapSensorName, trapEvent, trapSeverity, trapEventCode, trapServerIdentity, trapLocation, trapTime }
      STATUS  current
      DESCRIPTION
              "PCIe Error Deassert"
      ::= { ariAddInCard 18 }
    
    ariChipSet OBJECT IDENTIFIER ::= {serverAlertTrapGroup 793}  
    
    alertPCHError NOTIFICATION-TYPE
      OBJECTS { trapSeq, trapSensorName, trapEvent, trapSeverity, trapEventCode, trapServerIdentity, trapLocation, trapTime }
      STATUS  current
      DESCRIPTION
              "Uncorrectable PCH error"
      ::= { ariChipSet 17 }
    
    alertPCHErrorDeassert NOTIFICATION-TYPE
      OBJECTS { trapSeq, trapSensorName, trapEvent, trapSeverity, trapEventCode, trapServerIdentity, trapLocation, trapTime }
      STATUS  current
      DESCRIPTION
              "Uncorrectable PCH error Deassert"
      ::= { ariChipSet 18 }
  
    ariUIDButton OBJECT IDENTIFIER ::= {serverAlertTrapGroup 788}  
    
    alertUIDButtonPressed NOTIFICATION-TYPE
      OBJECTS { trapSeq, trapSensorName, trapEvent, trapSeverity, trapEventCode, trapServerIdentity, trapLocation, trapTime }
      STATUS  current
      DESCRIPTION
              "UID button pressed"
      ::= { ariUIDButton 17 }


  
    ariPowerCapping OBJECT IDENTIFIER ::= {serverAlertTrapGroup 1042}  
    
    alertPowerCapFail NOTIFICATION-TYPE
      OBJECTS { trapSeq, trapSensorName, trapEvent, trapSeverity, trapEventCode, trapServerIdentity, trapLocation, trapTime }
      STATUS  current
      DESCRIPTION
              "Power capping fail assert"
      ::= { ariPowerCapping 17 }

    alertPowerCapFailDeassert NOTIFICATION-TYPE
      OBJECTS { trapSeq, trapSensorName, trapEvent, trapSeverity, trapEventCode, trapServerIdentity, trapLocation, trapTime }
      STATUS  current
      DESCRIPTION
              "Power capping fail deassert"
      ::= { ariPowerCapping 18 }

  
    ariCardFault OBJECT IDENTIFIER ::= {serverAlertTrapGroup 1047}  
    
    alertCardStatusFault NOTIFICATION-TYPE
      OBJECTS { trapSeq, trapSensorName, trapEvent, trapSeverity, trapEventCode, trapServerIdentity, trapLocation, trapTime }
      STATUS  current
      DESCRIPTION
              "Raid or nic card fault "
      ::= { ariCardFault 17 }

    alertCardStatusFaultDeassert NOTIFICATION-TYPE
      OBJECTS { trapSeq, trapSensorName, trapEvent, trapSeverity, trapEventCode, trapServerIdentity, trapLocation, trapTime }
      STATUS  current
      DESCRIPTION
              "Raid or nic card fault deassert"
      ::= { ariCardFault 18 }
    

    ariLCD OBJECT IDENTIFIER ::= {serverAlertTrapGroup 1052}
    alertLCDFault NOTIFICATION-TYPE
      OBJECTS { trapSeq, trapSensorName, trapEvent, trapSeverity, trapEventCode, trapServerIdentity, trapLocation, trapTime }
      STATUS  current
      DESCRIPTION
              "LCD fault "
      ::= { ariLCD 17 }

    alertLCDFaultDeassert NOTIFICATION-TYPE
      OBJECTS { trapSeq, trapSensorName, trapEvent, trapSeverity, trapEventCode, trapServerIdentity, trapLocation, trapTime }
      STATUS  current
      DESCRIPTION
              "LCD fault deassert"
      ::= { ariLCD 18 }



    ariCPUUsage OBJECT IDENTIFIER ::= {serverAlertTrapGroup 1287}
    alertCPUUsageHigh NOTIFICATION-TYPE
      OBJECTS { trapSeq, trapSensorName, trapEvent, trapSeverity, trapEventCode, trapServerIdentity, trapLocation, trapTime }
      STATUS  current
      DESCRIPTION
              "CPU usage over threshold "
      ::= { ariCPUUsage 17 }

    alertCPUUsageHighDeassert NOTIFICATION-TYPE
      OBJECTS { trapSeq, trapSensorName, trapEvent, trapSeverity, trapEventCode, trapServerIdentity, trapLocation, trapTime }
      STATUS  current
      DESCRIPTION
              "CPU usage over threshold deassert"
      ::= { ariCPUUsage 18 }



    ariMemoryUsage OBJECT IDENTIFIER ::= {serverAlertTrapGroup 1292}

    alertMemoryUsageHigh NOTIFICATION-TYPE
      OBJECTS { trapSeq, trapSensorName, trapEvent, trapSeverity, trapEventCode, trapServerIdentity, trapLocation, trapTime }
      STATUS  current
      DESCRIPTION
              "Memory usage over threshold "
      ::= { ariMemoryUsage 17 }

    alertMemoryUsageHighDeassert NOTIFICATION-TYPE
      OBJECTS { trapSeq, trapSensorName, trapEvent, trapSeverity, trapEventCode, trapServerIdentity, trapLocation, trapTime }
      STATUS  current
      DESCRIPTION
              "Memory usage over threshold deassert"
      ::= { ariMemoryUsage 18 }


    ariDiskUsage OBJECT IDENTIFIER ::= {serverAlertTrapGroup 1293}

    alertDiskUsageHigh NOTIFICATION-TYPE
      OBJECTS { trapSeq, trapSensorName, trapEvent, trapSeverity, trapEventCode, trapServerIdentity, trapLocation, trapTime }
      STATUS  current
      DESCRIPTION
              "Disk usage over threshold "
      ::= { ariDiskUsage 17 }

    alertDiskUsageHighDeassert NOTIFICATION-TYPE
      OBJECTS { trapSeq, trapSensorName, trapEvent, trapSeverity, trapEventCode, trapServerIdentity, trapLocation, trapTime }
      STATUS  current
      DESCRIPTION
              "Disk usage over threshold deassert"
      ::= { ariDiskUsage 18 }
    

    ariSysNotice OBJECT IDENTIFIER ::= {serverAlertTrapGroup 1810}

    alertSystemWarmReset NOTIFICATION-TYPE
      OBJECTS { trapSeq, trapSensorName, trapEvent, trapSeverity, trapEventCode, trapServerIdentity, trapLocation, trapTime }
      STATUS  current
      DESCRIPTION
              "Uncorrectable system error. Unable to locate the specific failure, please warm reset the host to try to solve the problem"
      ::= { ariSysNotice 129 }
    
    alertSystemWarmResetDeassert NOTIFICATION-TYPE
      OBJECTS { trapSeq, trapSensorName, trapEvent, trapSeverity, trapEventCode, trapServerIdentity, trapLocation, trapTime }
      STATUS  current
      DESCRIPTION
              "Uncorrectable system error deassert"
      ::= { ariSysNotice 130 }
     

    ariModule OBJECT IDENTIFIER ::= {serverAlertTrapGroup 1813}

    alertModuleCritical NOTIFICATION-TYPE
      OBJECTS { trapSeq, trapSensorName, trapEvent, trapSeverity, trapEventCode, trapServerIdentity, trapLocation, trapTime }
      STATUS  current
      DESCRIPTION
              "transition to Critical from less severe"
      ::= { ariModule 33 }
  
    ariPSPresenceStatus OBJECT IDENTIFIER ::= {serverAlertTrapGroup 2057}  
    
    alertPSPresence NOTIFICATION-TYPE
      OBJECTS { trapSeq, trapSensorName, trapEvent, trapSeverity, trapEventCode, trapServerIdentity, trapLocation, trapTime }
      STATUS  current
      DESCRIPTION
              "power supply presence "
      ::= { ariPSPresenceStatus 17 }

    alertPSPresenceDeassert NOTIFICATION-TYPE
      OBJECTS { trapSeq, trapSensorName, trapEvent, trapSeverity, trapEventCode, trapServerIdentity, trapLocation, trapTime }
      STATUS  current
      DESCRIPTION
              "power supply presence deassert"
      ::= { ariPSPresenceStatus 18 }
  
    ariFanPresenceStatus OBJECT IDENTIFIER ::= {serverAlertTrapGroup 2058}  
    
    alertFanAbsent NOTIFICATION-TYPE
      OBJECTS { trapSeq, trapSensorName, trapEvent, trapSeverity, trapEventCode, trapServerIdentity, trapLocation, trapTime }
      STATUS  current
      DESCRIPTION
              "fan absent "
      ::= { ariFanPresenceStatus 1 }

    alertFanAbsentDeassert NOTIFICATION-TYPE
      OBJECTS { trapSeq, trapSensorName, trapEvent, trapSeverity, trapEventCode, trapServerIdentity, trapLocation, trapTime }
      STATUS  current
      DESCRIPTION
              "fan absent deassert"
      ::= { ariFanPresenceStatus 2 }     

  
    ariCardPresenceStatus OBJECT IDENTIFIER ::= {serverAlertTrapGroup 2071}  
    
    alertCardPresence NOTIFICATION-TYPE
      OBJECTS { trapSeq, trapSensorName, trapEvent, trapSeverity, trapEventCode, trapServerIdentity, trapLocation, trapTime }
      STATUS  current
      DESCRIPTION
              "card presence "
      ::= { ariCardPresenceStatus 17 }

    alertCardPresenceDeassert NOTIFICATION-TYPE
      OBJECTS { trapSeq, trapSensorName, trapEvent, trapSeverity, trapEventCode, trapServerIdentity, trapLocation, trapTime }
      STATUS  current
      DESCRIPTION
              "card presence deassert"
      ::= { ariCardPresenceStatus 18 }  

    ariLCDPresenceStatus OBJECT IDENTIFIER ::= {serverAlertTrapGroup 2076}  
    
    alertLCDAbsent NOTIFICATION-TYPE
      OBJECTS { trapSeq, trapSensorName, trapEvent, trapSeverity, trapEventCode, trapServerIdentity, trapLocation, trapTime }
      STATUS  current
      DESCRIPTION
              "LCD absent"
      ::= { ariLCDPresenceStatus 1 }

    alertLCDAbsentDeassert NOTIFICATION-TYPE
      OBJECTS { trapSeq, trapSensorName, trapEvent, trapSeverity, trapEventCode, trapServerIdentity, trapLocation, trapTime }
      STATUS  current
      DESCRIPTION
              "LCD absent deassert"
      ::= { ariLCDPresenceStatus 2 }     
  
      
    ariCPUCore OBJECT IDENTIFIER ::= {serverAlertTrapGroup 2311}
    
    alertCPUCoreIsolation NOTIFICATION-TYPE
      OBJECTS { trapSeq, trapSensorName, trapEvent, trapSeverity, trapEventCode, trapServerIdentity, trapLocation, trapTime }
      STATUS  current
      DESCRIPTION
              "CPU core isolation"
      ::= { ariCPUCore 1 }

    alertCPUCoreIsolationDeassert NOTIFICATION-TYPE
      OBJECTS { trapSeq, trapSensorName, trapEvent, trapSeverity, trapEventCode, trapServerIdentity, trapLocation, trapTime }
      STATUS  current
      DESCRIPTION
              "CPU core isolation deassert"
      ::= { ariCPUCore 2 }
    

    ariBMCBootUp OBJECT IDENTIFIER ::= {serverAlertTrapGroup 2326}  
    
    alertBMCBootUpAssert NOTIFICATION-TYPE
      OBJECTS { trapSeq, trapSensorName, trapEvent, trapSeverity, trapEventCode, trapServerIdentity, trapLocation, trapTime }
      STATUS  current
      DESCRIPTION
              "BMC boot up"
      ::= { ariBMCBootUp 17 }

  
    ariMemoryRiser OBJECT IDENTIFIER ::= {serverAlertTrapGroup 2583}

    alertMemoryRiserOnline NOTIFICATION-TYPE
      OBJECTS { trapSeq, trapSensorName, trapEvent, trapSeverity, trapEventCode, trapServerIdentity, trapLocation, trapTime }
      STATUS  current
      DESCRIPTION
              "Memory board online "
      ::= { ariMemoryRiser 49 }

    alertMemoryRiserOnlineDeassert NOTIFICATION-TYPE
      OBJECTS { trapSeq, trapSensorName, trapEvent, trapSeverity, trapEventCode, trapServerIdentity, trapLocation, trapTime }
      STATUS  current
      DESCRIPTION
              "Memory board online deassert"
      ::= { ariMemoryRiser 50 }

    alertMemoryRiserOffline NOTIFICATION-TYPE
      OBJECTS { trapSeq, trapSensorName, trapEvent, trapSeverity, trapEventCode, trapServerIdentity, trapLocation, trapTime }
      STATUS  current
      DESCRIPTION
              "Memory board offline "
      ::= { ariMemoryRiser 65 }

    alertMemoryRiserOfflineDeassert NOTIFICATION-TYPE
      OBJECTS { trapSeq, trapSensorName, trapEvent, trapSeverity, trapEventCode, trapServerIdentity, trapLocation, trapTime }
      STATUS  current
      DESCRIPTION
              "Memory board offline deassert"
      ::= { ariMemoryRiser 66 }
      
    alertMemoryRiserInstallError NOTIFICATION-TYPE
      OBJECTS { trapSeq, trapSensorName, trapEvent, trapSeverity, trapEventCode, trapServerIdentity, trapLocation, trapTime }
      STATUS  current
      DESCRIPTION
              "Memory riser install error "
      ::= { ariMemoryRiser 129 }

    alertMemoryRiserInstallErrorDeassert NOTIFICATION-TYPE
      OBJECTS { trapSeq, trapSensorName, trapEvent, trapSeverity, trapEventCode, trapServerIdentity, trapLocation, trapTime }
      STATUS  current
      DESCRIPTION
              "Memory riser install error deassert"
      ::= { ariMemoryRiser 130 }



    ariPSRedundancy OBJECT IDENTIFIER ::= {serverAlertTrapGroup 2824}
    
    alertPSRedundancyLost NOTIFICATION-TYPE
      OBJECTS { trapSeq, trapSensorName, trapEvent, trapSeverity, trapEventCode, trapServerIdentity, trapLocation, trapTime }
      STATUS  current
      DESCRIPTION
              "PS Redundancy lost"
      ::= { ariPSRedundancy 17 }

    alertPSRedundancyLostDeassert NOTIFICATION-TYPE
      OBJECTS { trapSeq, trapSensorName, trapEvent, trapSeverity, trapEventCode, trapServerIdentity, trapLocation, trapTime }
      STATUS  current
      DESCRIPTION
              "PS Redundancy lost deassert"
      ::= { ariPSRedundancy 18 }
      

      
--    ****** END trap Location ******************************* 



wired-for-management  OBJECT IDENTIFIER ::= {enterprises 3183}
pet     OBJECT IDENTIFIER ::= {wired-for-management 1}
--**************************************************************************
--*    Notifications (using SNMPv1 TRAP-TYPE constructs for maximum
--*     compatibility with deployed SNMP managers).
--**************************************************************************

pet-events    OBJECT IDENTIFIER ::= {pet 1}
--**************************************************************************
-- Temperature Sensor Events (16 of them)
--**************************************************************************

-- Event Sensor Type, Event Type, Event Offset (010100h == 65792)
tempTrapV1LowerNonCriticalGoingLow TRAP-TYPE
  ENTERPRISE  pet-events
  DESCRIPTION
    "Temperature sensor crossed lower non-critical threshold, going low. - Asserted"
    ::= 65792

-- Event Sensor Type, Event Type, Event Offset (010101h == 65793)
tempTrapV1LowerNonCriticalGoingHigh TRAP-TYPE
  ENTERPRISE  pet-events
  DESCRIPTION
    "Temperature sensor crossed lower non-critical threshold, going high. - Asserted"
    ::= 65793
    
-- Event Sensor Type, Event Type, Event Offset (010102h == 65794)
tempTrapV1LowerCriticalGoingLow TRAP-TYPE
  ENTERPRISE  pet-events
  DESCRIPTION
    "Temperature sensor crossed lower critical threshold, going low. - Asserted"
    ::= 65794

-- Event Sensor Type, Event Type, Event Offset (010103h == 65795)
tempTrapV1LowerCriticalGoingHigh TRAP-TYPE
  ENTERPRISE  pet-events
  DESCRIPTION
    "Temperature sensor crossed lower critical threshold, going high. - Asserted"
    ::= 65795

-- Event Sensor Type, Event Type, Event Offset (010106h == 65798)
tempTrapV1UpperNonCriticalGoingLow TRAP-TYPE
  ENTERPRISE  pet-events
  DESCRIPTION
    "Temperature sensor crossed upper non-critical threshold, going low. - Asserted"
    ::= 65798

-- Event Sensor Type, Event Type, Event Offset (010107h == 65799)
tempTrapV1UpperNonCriticalGoingHigh TRAP-TYPE
  ENTERPRISE  pet-events
  DESCRIPTION
    "Temperature sensor crossed upper non-critical threshold, going high. - Asserted"
    ::= 65799

-- Event Sensor Type, Event Type, Event Offset (010108h == 65800)
tempTrapV1UpperCriticalGoingLow TRAP-TYPE
  ENTERPRISE  pet-events
  DESCRIPTION
    "Temperature sensor crossed upper critical threshold, going low. - Asserted"
    ::= 65800

-- Event Sensor Type, Event Type, Event Offset (010109h == 65801)
tempTrapV1UpperCriticalGoingHigh TRAP-TYPE
  ENTERPRISE  pet-events
  DESCRIPTION
    "Temperature sensor crossed upper critical threshold, going high. - Asserted"
    ::= 65801
    
-- Event Sensor Type, Event Type, Event Offset (01010Bh == 65803)
tempTrapV1UpperNonRecoverableGoingHigh TRAP-TYPE
  ENTERPRISE  pet-events
  DESCRIPTION
    "Temperature sensor crossed upper non-recoverable threshold, going high. - Asserted"
    ::= 65803
	
-- Event Sensor Type, Event Type, Event Offset (010180h == 65920)
tempTrapV1LowerNonCriticalGoingLowClear TRAP-TYPE
  ENTERPRISE  pet-events
  DESCRIPTION
    "Temperature sensor crossed lower non-critical threshold, going low. - Deasserted"
    ::= 65920

-- Event Sensor Type, Event Type, Event Offset (010181h == 65921)
tempTrapV1LowerNonCriticalGoingHighClear TRAP-TYPE
  ENTERPRISE  pet-events
  DESCRIPTION
    "Temperature sensor crossed lower non-critical threshold, going high. - Deasserted"
    ::= 65921

-- Event Sensor Type, Event Type, Event Offset (010182h == 65922)
tempTrapV1LowerCriticalGoingLowClear TRAP-TYPE
  ENTERPRISE  pet-events
  DESCRIPTION
    "Temperature sensor crossed lower critical threshold, going low. - Deasserted"
    ::= 65922

-- Event Sensor Type, Event Type, Event Offset (010183h == 65923)
tempTrapV1LowerCriticalGoingHighClear TRAP-TYPE
  ENTERPRISE  pet-events
  DESCRIPTION
    "Temperature sensor crossed lower critical threshold, going high. - Deasserted"
    ::= 65923

-- Event Sensor Type, Event Type, Event Offset (010186h == 65926)
tempTrapV1UpperNonCriticalGoingLowClear TRAP-TYPE
  ENTERPRISE  pet-events
  DESCRIPTION
    "Temperature sensor crossed upper non-critical threshold, going low. - Deasserted"
    ::= 65926

-- Event Sensor Type, Event Type, Event Offset (010187h == 65927)
tempTrapV1UpperNonCriticalGoingHighClear TRAP-TYPE
  ENTERPRISE  pet-events
  DESCRIPTION
    "Temperature sensor crossed upper non-critical threshold, going high. - Deasserted"
    ::= 65927

-- Event Sensor Type, Event Type, Event Offset (010188h == 65928)
tempTrapV1UpperCriticalGoingLowClear TRAP-TYPE
  ENTERPRISE  pet-events
  DESCRIPTION
    "Temperature sensor crossed upper critical threshold, going low. - Deasserted"
    ::= 65928

-- Event Sensor Type, Event Type, Event Offset (010189h == 65929)
tempTrapV1UpperCriticalGoingHighClear TRAP-TYPE
  ENTERPRISE  pet-events
  DESCRIPTION
    "Temperature sensor crossed upper critical threshold, going high. - Deasserted"
    ::= 65929
	
-- Event Sensor Type, Event Type, Event Offset (01018Bh == 65931)
tempTrapV1UpperNonRecoverableGoingHighClear TRAP-TYPE
  ENTERPRISE  pet-events
  DESCRIPTION
    "Temperature sensor crossed upper non-recoverable threshold, going high. - Deasserted"
    ::= 65931	
	

--**************************************************************************
-- Voltage Sensor Events (16 of them)
--**************************************************************************

-- Event Sensor Type, Event Type, Event Offset (020100h == 131328)
voltageTrapV1LowerNonCriticalGoingLow TRAP-TYPE
  ENTERPRISE  pet-events
  DESCRIPTION
    "Voltage sensor crossed lower non-critical threshold, going low - Asserted."

    ::= 131328

-- Event Sensor Type, Event Type, Event Offset (020101h == 131329)
voltageTrapV1LowerNonCriticalGoingHigh TRAP-TYPE
  ENTERPRISE  pet-events
  DESCRIPTION
    "Voltage sensor crossed lower non-critical threshold, going high - Asserted."

    ::= 131329

-- Event Sensor Type, Event Type, Event Offset (020102h == 131330)
voltageTrapV1LowerCriticalGoingLow TRAP-TYPE
  ENTERPRISE  pet-events
  DESCRIPTION
    "Voltage sensor crossed lower critical threshold, going low - Asserted."
    ::= 131330

-- Event Sensor Type, Event Type, Event Offset (020103h == 131331)
voltageTrapV1LowerCriticalGoingHigh TRAP-TYPE
  ENTERPRISE  pet-events
  DESCRIPTION
    "Voltage sensor crossed lower critical threshold, going high - Asserted."
    ::= 131331

-- Event Sensor Type, Event Type, Event Offset (020104h == 131332)
voltageTrapV1LowerNonRecoverableGoingLow TRAP-TYPE
  ENTERPRISE  pet-events
  DESCRIPTION
    "Voltage sensor crossed lower non-recoverable threshold, going low - Asserted."
    ::= 131332	
	
-- Event Sensor Type, Event Type, Event Offset (020106h == 131334)
voltageTrapV1UpperNonCriticalGoingLow TRAP-TYPE
  ENTERPRISE  pet-events
  DESCRIPTION
    "Voltage sensor crossed upper non-critical threshold, going low - Asserted."
    ::= 131334

-- Event Sensor Type, Event Type, Event Offset (020107h == 131335)
voltageTrapV1UpperNonCriticalGoingHigh TRAP-TYPE
  ENTERPRISE  pet-events
  DESCRIPTION
    "Voltage sensor crossed upper non-critical threshold, going high - Asserted."
    ::= 131335

-- Event Sensor Type, Event Type, Event Offset (020108h == 131336)
voltageTrapV1UpperCriticalGoingLow TRAP-TYPE
  ENTERPRISE  pet-events
  DESCRIPTION
    "Voltage sensor crossed upper critical threshold, going low - Asserted."
    ::= 131336

-- Event Sensor Type, Event Type, Event Offset (020109h == 131337)
voltageTrapV1UpperCriticalGoingHigh TRAP-TYPE
  ENTERPRISE  pet-events
  DESCRIPTION
    "Voltage sensor crossed upper critical threshold, going high - Asserted."
    ::= 131337
	
-- Event Sensor Type, Event Type, Event Offset (02010Bh == 131339)
voltageTrapV1UpperNonRecoverableGoingHigh TRAP-TYPE
  ENTERPRISE  pet-events
  DESCRIPTION
    "Voltage sensor crossed upper non-recoverable threshold, going high - Asserted."
    ::= 131339
	
-- Event Sensor Type, Event Type, Event Offset (020180h == 131456)
voltageTrapV1LowerNonCriticalGoingLowClear TRAP-TYPE
  ENTERPRISE  pet-events
  DESCRIPTION
    "Voltage sensor crossed lower non-critical threshold, going low - Deasserted."

    ::= 131456

-- Event Sensor Type, Event Type, Event Offset (020181h == 131457)
voltageTrapV1LowerNonCriticalGoingHighClear TRAP-TYPE
  ENTERPRISE  pet-events
  DESCRIPTION
    "Voltage sensor crossed lower non-critical threshold, going high - Deasserted."

    ::= 131457

-- Event Sensor Type, Event Type, Event Offset (020182h == 131458)
voltageTrapV1LowerCriticalGoingLowClear TRAP-TYPE
  ENTERPRISE  pet-events
  DESCRIPTION
    "Voltage sensor crossed lower critical threshold, going low - Deasserted."
    ::= 131458

-- Event Sensor Type, Event Type, Event Offset (020183h == 131459)
voltageTrapV1LowerCriticalGoingHighClear TRAP-TYPE
  ENTERPRISE  pet-events
  DESCRIPTION
    "Voltage sensor crossed lower critical threshold, going high - Deasserted."
    ::= 131459

-- Event Sensor Type, Event Type, Event Offset (020184h == 131460)
voltageTrapV1UpperNonRecoverableGoingLowClear TRAP-TYPE
  ENTERPRISE  pet-events
  DESCRIPTION
    "Voltage sensor crossed upper non-recoverable threshold, going low - Deasserted."
    ::= 131460
	
-- Event Sensor Type, Event Type, Event Offset (020186h == 131462)
voltageTrapV1UpperNonCriticalGoingLowClear TRAP-TYPE
  ENTERPRISE  pet-events
  DESCRIPTION
    "Voltage sensor crossed upper non-critical threshold, going low - Deasserted."
    ::= 131462

-- Event Sensor Type, Event Type, Event Offset (020187h == 131463)
voltageTrapV1UpperNonCriticalGoingHighClear TRAP-TYPE
  ENTERPRISE  pet-events
  DESCRIPTION
    "Voltage sensor crossed upper non-critical threshold, going high - Deasserted."
    ::= 131463

-- Event Sensor Type, Event Type, Event Offset (020188h == 131464)
voltageTrapV1UpperCriticalGoingLowClear TRAP-TYPE
  ENTERPRISE  pet-events
  DESCRIPTION
    "Voltage sensor crossed upper critical threshold, going low - Deasserted."
    ::= 131464

-- Event Sensor Type, Event Type, Event Offset (020189h == 131465)
voltageTrapV1UpperCriticalGoingHighClear TRAP-TYPE
  ENTERPRISE  pet-events
  DESCRIPTION
    "Voltage sensor crossed upper critical threshold, going high - Deasserted."
    ::= 131465

-- Event Sensor Type, Event Type, Event Offset (02018Bh == 131467)
voltageTrapV1UpperNonRecoverableGoingHighClear TRAP-TYPE
  ENTERPRISE  pet-events
  DESCRIPTION
    "Voltage sensor crossed upper non-recoverable threshold, going high - Deasserted."
    ::= 131467

--**************************************************************************
-- Current Sensor Events ( 6 of them)
--**************************************************************************
-- Event Sensor Type, Event Type, Event Offset (030107h == 196871)
currentTrapV1UpperNonCriticalGoingHigh TRAP-TYPE
  ENTERPRISE  pet-events
  DESCRIPTION
    "Current sensor crossed upper non-critical threshold, going high - Asserted."
    ::= 196871
	
-- Event Sensor Type, Event Type, Event Offset (030109h == 196873)
currentTrapV1UpperCriticalGoingHigh TRAP-TYPE
  ENTERPRISE  pet-events
  DESCRIPTION
    "Current sensor crossed upper critical threshold, going high - Asserted."
    ::= 196873

-- Event Sensor Type, Event Type, Event Offset (03010Bh == 196875)
currentTrapV1UpperNonRecoverableGoingHigh TRAP-TYPE
  ENTERPRISE  pet-events
  DESCRIPTION
    "Current sensor crossed upper non-recoverable threshold, going high - Asserted."
    ::= 196875
	
-- Event Sensor Type, Event Type, Event Offset (030187h == 196999)
currentTrapV1UpperNonCriticalGoingHighClear TRAP-TYPE
  ENTERPRISE  pet-events
  DESCRIPTION
    "Current sensor crossed upper non-critical threshold, going high - Deasserted."
    ::= 196999
	
-- Event Sensor Type, Event Type, Event Offset (030189h == 197001)
currentTrapV1UpperCriticalGoingHighClear TRAP-TYPE
  ENTERPRISE  pet-events
  DESCRIPTION
    "Current sensor crossed upper critical threshold, going high - Deasserted."
    ::= 197001

-- Event Sensor Type, Event Type, Event Offset (03018Bh == 197003)
currentTrapV1UpperNonRecoverableGoingHighClear TRAP-TYPE
  ENTERPRISE  pet-events
  DESCRIPTION
    "Current sensor crossed upper non-recoverable threshold, going high - Deasserted."
    ::= 197003
	
--**************************************************************************
-- Fan Failure Events (8 of them)
--**************************************************************************

-- Event Sensor Type, Event Type, Event Offset (040100h == 262400)
fanFailureLowerNonCriticalGoingLow TRAP-TYPE
  ENTERPRISE  pet-events
  DESCRIPTION
    "Fan sensor crossed lower non-critical threshold, going low - Asserted."
    ::= 262400

-- Event Sensor Type, Event Type, Event Offset (040101h == 262401)
fanFailureLowerNonCriticalGoingHigh TRAP-TYPE
  ENTERPRISE  pet-events
  DESCRIPTION
    "Fan sensor crossed lower non-critical threshold, going high - Asserted."
    ::= 262401

-- Event Sensor Type, Event Type, Event Offset (040102h == 262402)
fanFailureLowerCriticalGoingLow TRAP-TYPE
  ENTERPRISE  pet-events
  DESCRIPTION
    "Fan sensor crossed lower critical threshold, going low - Asserted."

    ::= 262402

-- Event Sensor Type, Event Type, Event Offset (040103h == 262403)
fanFailureLowerCriticalGoingHigh TRAP-TYPE
  ENTERPRISE  pet-events
  DESCRIPTION
    "Fan sensor crossed lower critical threshold, going high - Asserted."

    ::= 262403

-- Event Sensor Type, Event Type, Event Offset (040104h == 262404)
fanFailureLowerNonRecoverableGoingLow TRAP-TYPE
  ENTERPRISE  pet-events
  DESCRIPTION
    "Fan sensor crossed lower non-recoverable threshold, going low - Asserted."
    ::= 262404
	
-- Event Sensor Type, Event Type, Event Offset (040180h == 262528)
fanFailureLowerNonCriticalGoingLowClear TRAP-TYPE
  ENTERPRISE  pet-events
  DESCRIPTION
    "Fan sensor crossed lower non-critical threshold, going low - Deasserted."
    ::= 262528

-- Event Sensor Type, Event Type, Event Offset (040181h == 262529)
fanFailureLowerNonCriticalGoingHighClear TRAP-TYPE
  ENTERPRISE  pet-events
  DESCRIPTION
    "Fan sensor crossed lower non-critical threshold, going high - Deasserted."
    ::= 262529

-- Event Sensor Type, Event Type, Event Offset (040182h == 262530)
fanFailureLowerCriticalGoingLowClear TRAP-TYPE
  ENTERPRISE  pet-events
  DESCRIPTION
    "Fan sensor crossed lower critical threshold, going low - Deasserted."

    ::= 262530

-- Event Sensor Type, Event Type, Event Offset (040183h == 262531)
fanFailureLowerCriticalGoingHighClear TRAP-TYPE
  ENTERPRISE  pet-events
  DESCRIPTION
    "Fan sensor crossed lower critical threshold, going high - Deasserted."

    ::= 262531
	
-- Event Sensor Type, Event Type, Event Offset (040184h == 262532)
fanFailureLowerNonRecoverableGoingLowClear TRAP-TYPE
  ENTERPRISE  pet-events
  DESCRIPTION
    "Fan sensor crossed lower non-recoverable threshold, going low - Deasserted."
    ::= 262532

--**************************************************************************
-- Fan Supply Fault Events (4 of them)
--**************************************************************************	
-- Event Sensor Type, Event Type, Event Offset (040802h == 264192)
fanDeviceAbsence TRAP-TYPE
  ENTERPRISE  pet-events
  DESCRIPTION
    "Fan device removed/absent event - Asserted."
    ::= 264192
	
-- Event Sensor Type, Event Type, Event Offset (040801h == 264193)
fanDevicePresence TRAP-TYPE
  ENTERPRISE  pet-events
  DESCRIPTION
    "Fan device inserted/present event - Asserted."
    ::= 264193
	
-- Event Sensor Type, Event Type, Event Offset (04080Dh == 264205)
fanDeviceHotPlug TRAP-TYPE
  ENTERPRISE  pet-events
  DESCRIPTION
    "Fan device hot plug event - Asserted."
    ::= 264205

-- Event Sensor Type, Event Type, Event Offset (04088Dh == 264333)
fanDeviceHotPlugClear TRAP-TYPE
  ENTERPRISE  pet-events
  DESCRIPTION
    "Fan device hot plug event - Deasserted."
    ::= 264333

--**************************************************************************
-- Chassis Intrusion Event
--**************************************************************************

-- Event Sensor Type 05h, Event Type 6fh, Event Offset 00h (056f00h == 356096)
chassisIntrusionEvent TRAP-TYPE
  ENTERPRISE  pet-events
  DESCRIPTION
    "A Chassis Intrusion assertion event."

    ::= 356096

-- Event Sensor Type 05h, Event Type 6fh, Event Offset 04h (056f04h == 356100)
chassisIntrusionEventLANLeashLost TRAP-TYPE
  ENTERPRISE  pet-events
  DESCRIPTION
    "A Chassis Intrusion LAN leash lost assertion event."

    ::= 356100

-- Event Sensor Type 05h, Event Type 6fh, Event Offset 00h (056f80h == 356224)
chassisIntrusionEventClear TRAP-TYPE
  ENTERPRISE  pet-events
  DESCRIPTION
    "A Chassis Intrusion Deassertion event."

    ::= 356224

-- Event Sensor Type 05h, Event Type 6fh, Event Offset 04h (056f84h == 356228)
chassisIntrusionEventLANLeashLostClear TRAP-TYPE
  ENTERPRISE  pet-events
  DESCRIPTION
    "A Chassis Intrusion LAN leash lost de-assertion event."

    ::= 356228

--**************************************************************************
-- Power Sensor Events ( 6 of them)
--**************************************************************************
-- Event Sensor Type, Event Type, Event Offset (080107h == 524551)
powerTrapV1UpperNonCriticalGoingHigh TRAP-TYPE
  ENTERPRISE  pet-events
  DESCRIPTION
    "Power sensor crossed upper non-critical threshold, going high - Asserted."
    ::= 524551

-- Event Sensor Type, Event Type, Event Offset (080109h == 524553)
powerTrapV1UpperCriticalGoingHigh TRAP-TYPE
  ENTERPRISE  pet-events
  DESCRIPTION
    "Power sensor crossed upper critical threshold, going high - Asserted."
    ::= 524553

-- Event Sensor Type, Event Type, Event Offset (08010Bh == 524555)
powerTrapV1UpperNonRecoverableGoingHigh TRAP-TYPE
  ENTERPRISE  pet-events
  DESCRIPTION
    "Power sensor crossed upper non-recoverable threshold, going high - Asserted."
    ::= 524555	
	
-- Event Sensor Type, Event Type, Event Offset (080187h == 524679)
powerTrapV1UpperNonCriticalGoingHighClear TRAP-TYPE
  ENTERPRISE  pet-events
  DESCRIPTION
    "Power sensor crossed upper non-critical threshold, going high - Deasserted."
    ::= 524679

-- Event Sensor Type, Event Type, Event Offset (080189h == 524681)
powerTrapV1UpperCriticalGoingHighClear TRAP-TYPE
  ENTERPRISE  pet-events
  DESCRIPTION
    "Power sensor crossed upper critical threshold, going high - Deasserted."
    ::= 524681

-- Event Sensor Type, Event Type, Event Offset (08018Bh == 524683)
powerTrapV1UpperNonRecoverableGoingHighClear TRAP-TYPE
  ENTERPRISE  pet-events
  DESCRIPTION
    "Power sensor crossed upper non-recoverable threshold, going high - Deasserted."
    ::= 524683		
	
--**************************************************************************
-- Power Supply Fault Events (10 of them)
--**************************************************************************

-- Event Sensor Type, Event Type, Event Offset (086F00h == 552704)
powerSupplyPresence TRAP-TYPE
    ENTERPRISE  pet-events
    DESCRIPTION
        "Power supply presence event - Asserted."
    ::= 552704

-- Event Sensor Type, Event Type, Event Offset (086F01h == 552705)
powerSupplyFailure TRAP-TYPE
  ENTERPRISE  pet-events
  DESCRIPTION
    "Power supply failure event - Asserted."
    ::= 552705

-- Event Sensor Type, Event Type, Event Offset (086F02h == 552706)
powerSupplyPredictiveFailure TRAP-TYPE
  ENTERPRISE  pet-events
  DESCRIPTION
    "Power supply predictive failure event - Asserted."
    ::= 552706

-- Event Sensor Type, Event Type, Event Offset (086F03h == 552707)
powerSupplyACLost TRAP-TYPE
  ENTERPRISE  pet-events
  DESCRIPTION
    "Power supply A/C lost event - Asserted."
    ::= 552707

-- Event Sensor Type, Event Type, Event Offset (086F06h == 552710)
powerSupplyConfigurationError TRAP-TYPE
  ENTERPRISE  pet-events
  DESCRIPTION
    "Power supply configuration error event - Asserted."
    ::= 552710

-- Event Sensor Type, Event Type, Event Offset (086F0Dh == 552717)
powerSupplyHotPlug TRAP-TYPE
  ENTERPRISE  pet-events
  DESCRIPTION
    "Power supply hot plug event - Asserted."
    ::= 552717
	
-- Event Sensor Type, Event Type, Event Offset (086F80h == 552832)
powerSupplyPresenceClear TRAP-TYPE
    ENTERPRISE  pet-events
    DESCRIPTION
        "Power supply presence event - Deasserted."
    ::= 552832

-- Event Sensor Type, Event Type, Event Offset (086F81h == 552833)
powerSupplyFailureClear TRAP-TYPE
  ENTERPRISE  pet-events
  DESCRIPTION
    "Power supply failure event - Deasserted."
    ::= 552833

-- Event Sensor Type, Event Type, Event Offset (086F82h == 552834)
powerSupplyPredictiveFailureClear TRAP-TYPE
  ENTERPRISE  pet-events
  DESCRIPTION
    "Power supply predictive failure event - Deasserted."
    ::= 552834

-- Event Sensor Type, Event Type, Event Offset (086F83h == 552835)
powerSupplyACLostClear TRAP-TYPE
  ENTERPRISE  pet-events
  DESCRIPTION
    "Power supply A/C lost event - Deasserted."
    ::= 552835

-- Event Sensor Type, Event Type, Event Offset (086F86h == 552838)
powerSupplyConfigurationErrorClear TRAP-TYPE
  ENTERPRISE  pet-events
  DESCRIPTION
    "Power supply configuration error event - Deasserted."
    ::= 552838

--**************************************************************************
-- Uncorrectable ECC Error Event
--**************************************************************************

-- Event Sensor Type, Event Type, Event Offset (0C6F00h == 814848)
correctableECCError TRAP-TYPE
  ENTERPRISE  pet-events
  DESCRIPTION
    "Correctable ECC error event - Asserted."

    ::= 814848
    
-- Event Sensor Type, Event Type, Event Offset (0C6F01h == 814849)
uncorrectableECCError TRAP-TYPE
  ENTERPRISE  pet-events
  DESCRIPTION
    "Uncorrectable ECC error event - Asserted."

    ::= 814849
-- Event Sensor Type, Event Type, Event Offset (0C6F80h == 814976)
correctableECCErrorClear TRAP-TYPE
  ENTERPRISE  pet-events
  DESCRIPTION
    "Correctable ECC error event - Deasserted."

    ::= 814976
    
-- Event Sensor Type, Event Type, Event Offset (0C6F81h == 814977)
uncorrectableECCErrorClear TRAP-TYPE
  ENTERPRISE  pet-events
  DESCRIPTION
    "Uncorrectable ECC error event - Deasserted."

    ::= 814977
	
alertTrapV1MemoryMRCTraining TRAP-TYPE
  ENTERPRISE  pet-events
  DESCRIPTION
    "Memory MRC training warning event - Asserted."

    ::= 814859
	
alertTrapV1MemoryMRC TRAP-TYPE
  ENTERPRISE  pet-events
  DESCRIPTION
    "Memory MRC DRAM memtest errors - Asserted."
    ::= 814860

MemoryECCLimitation TRAP-TYPE
  ENTERPRISE  pet-events
  DESCRIPTION
    "Memory ECC Limit reached - Asserted."
    ::= 814853


--**************************************************************************
-- POST Error Event
--**************************************************************************

-- Event Sensor Type, Event Type, Event Offset (0F6F00h == 1011456)
postError TRAP-TYPE
  ENTERPRISE  pet-events
  DESCRIPTION
    "Power On Self Test (POST) error event - Asserted."

    ::= 1011456

-- Event Sensor Type, Event Type, Event Offset (0F6F80h == 1011584)
postErrorClear TRAP-TYPE
  ENTERPRISE  pet-events
  DESCRIPTION
    "Power On Self Test (POST) error event - Deasserted."

    ::= 1011584

--**************************************************************************
-- Processor Failure Events (8 of them)
--**************************************************************************

-- Event Sensor Type, Event Type, Event Offset (076F01h == 487169)
thermalTripError TRAP-TYPE
  ENTERPRISE  pet-events
  DESCRIPTION
    "Thermal Trip error event - Asserted."
    ::= 487169

-- Event Sensor Type, Event Type, Event Offset (076F07h == 487175)
cpuPresence TRAP-TYPE
  ENTERPRISE  pet-events
  DESCRIPTION
    "Processor Presence - Asserted"

    ::= 487175

-- Event Sensor Type, Event Type, Event Offset (076F08h == 487175)
cpuDisabled TRAP-TYPE
  ENTERPRISE  pet-events
  DESCRIPTION
    "Processor Disabled - Asserted"

    ::= 487175

-- Event Sensor Type, Event Type, Event Offset (070301h == 459521)
procDisabledError TRAP-TYPE
  ENTERPRISE  pet-events
  DESCRIPTION
    "CATERR Event Detected - Asserted."
    ::= 459521

-- Event Sensor Type, Event Type, Event Offset (076F81h == 487297)
thermalTripErrorClear TRAP-TYPE
  ENTERPRISE  pet-events
  DESCRIPTION
    "Thermal Trip error event - Deasserted."
    ::= 487297

-- Event Sensor Type, Event Type, Event Offset (076F87h == 487303)
cpuPresenceClear TRAP-TYPE
  ENTERPRISE  pet-events
  DESCRIPTION
    "Processor Presence - Deasserted"

    ::= 487303

-- Event Sensor Type, Event Type, Event Offset (076F88h == 487304)
cpuDisabledClear TRAP-TYPE
  ENTERPRISE  pet-events
  DESCRIPTION
    "Processor Disabled - Deasserted"

    ::= 487304

-- Event Sensor Type, Event Type, Event Offset (070381h == 459649)
procDisabledErrorClear TRAP-TYPE
  ENTERPRISE  pet-events
  DESCRIPTION
    "CATERR Event Detected - Deasserted."
    ::= 459649

-- Event Sensor Type, Event Type, Event Offset (76F0Ah == 487178 )
CPUAutomaticallyThrottled TRAP-TYPE
    ENTERPRISE  pet-events
    DESCRIPTION
        "CPU Automatically Throttled -Asserted."
    ::= 487178

-- Event Sensor Type, Event Type, Event Offset (76F0Bh == 487179 )
alertCPUMCE TRAP-TYPE
    ENTERPRISE  pet-events
    DESCRIPTION        
		"CPU Machine Check Exception (Uncorrectable) -Asserted."
    ::= 487179

-- Event Sensor Type, Event Type, Event Offset (76F00Bh == 487168 )
CPUCATError TRAP-TYPE
    ENTERPRISE  pet-events
    DESCRIPTION
        "CPU IERR -Asserted."
    ::= 487168

--**************************************************************************
-- Critical Interrupt Events (1 of them)
--**************************************************************************

-- Event Sensor Type, Event Type, Event Offset (136F00h == 1273600)
fatalNMIError TRAP-TYPE
  ENTERPRISE  pet-events
  DESCRIPTION
    "Front Panel NMI Assertion event - Asserted."
    ::= 1273600
    
-- Event Sensor Type, Event Type, Event Offset (136F80h == 1273728)
fatalNMIErrorClear TRAP-TYPE
  ENTERPRISE  pet-events
  DESCRIPTION
    "Front Panel NMI Assertion event - Deasserted."
    ::= 1273728

--**************************************************************************
-- PWR Events (2 of them)
--**************************************************************************	
-- Event Sensor Type, Event Type, Event Offset (226f00h == 2256640)
powerStateWorking TRAP-TYPE
  ENTERPRISE  pet-events
  DESCRIPTION
    "S0/G0 Working - Asserted."
    ::= 2256640
	
-- Event Sensor Type, Event Type, Event Offset (226f06h == 2256646)
powerStateSoftOff TRAP-TYPE
  ENTERPRISE  pet-events
  DESCRIPTION
    "S4/S5 Soft-off - Asserted."
    ::= 2256646	

--**************************************************************************
-- Watchdog 2 Events (5 of them)
--**************************************************************************
-- Event Sensor Type, Event Type, Event Offset (236F00h == 2322176)
timerExpired TRAP-TYPE
    ENTERPRISE  pet-events
    DESCRIPTION
        "Timer expired event."
    ::= 2322176

-- Event Sensor Type, Event Type, Event Offset (236F01h == 2322177)
hardReset TRAP-TYPE
  ENTERPRISE  pet-events
  DESCRIPTION
    "Hard reset event."
    ::= 2322177

-- Event Sensor Type, Event Type, Event Offset (236F02h == 2322178)
powerDown TRAP-TYPE
  ENTERPRISE  pet-events
  DESCRIPTION
    "Power down event."
    ::= 2322178

-- Event Sensor Type, Event Type, Event Offset (236F03h == 2322179)
powerReset TRAP-TYPE
  ENTERPRISE  pet-events
  DESCRIPTION
    "Power Reset event"
    ::= 2322179

-- Event Sensor Type, Event Type, Event Offset (236F08h == 2322184)
timerInterrupt TRAP-TYPE
  ENTERPRISE  pet-events
  DESCRIPTION
    "Timer Interrupt event."
    ::= 2322184
    

--**************************************************************************
-- System Event
--**************************************************************************

-- Event Sensor Type, Event Type, Event Offset (126F01h == 1208065)
oemSystemBootEvent TRAP-TYPE
  ENTERPRISE  pet-events
  DESCRIPTION
    "OEM System Boot event."
    ::= 1208065
	
-- Event Sensor Type, Event Type, Event Offset (126F05h == 1208069)
alertTrapV1TimestampClockSync TRAP-TYPE
  ENTERPRISE  pet-events
  DESCRIPTION
    "Timestamp Clock Synch - Asserted."
    ::= 1208069

-- Event Sensor Type, Event Type, Event Offset (106F02h == 1076994)
selLogAreaReset TRAP-TYPE
  ENTERPRISE  pet-events
  DESCRIPTION
    "Log area reset / cleared"
    ::=1076994

-- Event Sensor Type, Event Type, Event Offset (126F81h == 1077121)
oemSystemBootEventClear TRAP-TYPE
  ENTERPRISE  pet-events
  DESCRIPTION
    "OEM System Boot event - Deasserted."
    ::= 1077121

-- Event Sensor Type, Event Type, Event Offset (106F82h == 1077122)
selLogAreaResetClear TRAP-TYPE
  ENTERPRISE  pet-events
  DESCRIPTION
    "Log area reset / cleared - Deasserted"
    ::=1077122
    
    
--**************************************************************************
-- SMI Timeout
--**************************************************************************

-- Event Sensor Type, Event Type, Event Offset (03F301h == 258817)
smiTimeoutError TRAP-TYPE
    ENTERPRISE  pet-events
    DESCRIPTION
        "SMI Timeout Assertion event."
    ::= 258817    

-- Event Sensor Type, Event Type, Event Offset (03F381h == 258945)
smiTimeoutErrorDeassert TRAP-TYPE
    ENTERPRISE  pet-events
    DESCRIPTION
        "SMI Timeout Deassertion event."
    ::= 258945    
    
--**************************************************************************
-- Drive Slot (Bay) Offsets (8)
--**************************************************************************

-- Event Sensor Type, Event Type, Event Offset (0D6F00h == 880384)
drivePresence TRAP-TYPE
    ENTERPRISE  pet-events
    DESCRIPTION
        "Drive Presence event - Asserted."
    ::= 880384       
    
-- Event Sensor Type, Event Type, Event Offset (0D6F01h == 880385)
driveFault TRAP-TYPE
    ENTERPRISE  pet-events
    DESCRIPTION
        "Drive Fault event - Asserted."
    ::= 880385      
    
-- Event Sensor Type, Event Type, Event Offset (0D6F02h == 880386)
drivePredictiveFailure TRAP-TYPE
    ENTERPRISE  pet-events
    DESCRIPTION
        "Drive Predictive Failure event - Asserted."
    ::= 880386      
    
-- Event Sensor Type, Event Type, Event Offset (0D6F07h == 880391)
driveRebuild TRAP-TYPE
    ENTERPRISE  pet-events
    DESCRIPTION
        "Drive Rebuild event - Asserted."
    ::= 880391      
    
-- Event Sensor Type, Event Type, Event Offset (0D6F80h == 880512)
drivePresenceClear TRAP-TYPE
    ENTERPRISE  pet-events
    DESCRIPTION
        "Drive Presence event - Deasserted."
    ::= 880512       
    
-- Event Sensor Type, Event Type, Event Offset (0D6F81h == 880513)
driveFaultClear TRAP-TYPE
    ENTERPRISE  pet-events
    DESCRIPTION
        "Drive Fault event - Deasserted."
    ::= 880513      
    
-- Event Sensor Type, Event Type, Event Offset (0D6F82h == 880514)
drivePredictiveFailureClear TRAP-TYPE
    ENTERPRISE  pet-events
    DESCRIPTION
        "Drive Predictive Failure event - Deasserted."
    ::= 880514      
    
-- Event Sensor Type, Event Type, Event Offset (0D6F87h == 880519)
driveRebuildClear TRAP-TYPE
    ENTERPRISE  pet-events
    DESCRIPTION
        "Drive Rebuild event - Deasserted."
    ::= 880519  

-- Event Sensor Type, Event Type, Event Offset (0D6F0dh == 880397)
driveHotPlug TRAP-TYPE
    ENTERPRISE  pet-events
    DESCRIPTION
        "Drive HotPlug event - Asserted."
    ::= 880397

--**************************************************************************
-- Power Unit Offsets (8)
--**************************************************************************

-- Event Sensor Type, Event Type, Event Offset (096F00h == 618240)
powerOffPowerUnit TRAP-TYPE
    ENTERPRISE  pet-events
    DESCRIPTION
        "Power Unit Power Off event - Asserted."
    ::= 618240    
    
-- Event Sensor Type, Event Type, Event Offset (096F04h == 618244)
acLostPowerUnit TRAP-TYPE
    ENTERPRISE  pet-events
    DESCRIPTION
        "Power Unit AC Lost event - Asserted."
    ::= 618244   
    
-- Event Sensor Type, Event Type, Event Offset (096F05h == 618245)
softPowerControlPowerUnit TRAP-TYPE
    ENTERPRISE  pet-events
    DESCRIPTION
        "Power Unit Soft Power Control Failure event - Asserted."
    ::= 618245 
    
-- Event Sensor Type, Event Type, Event Offset (096F06h == 618246)
powerUnitFailure TRAP-TYPE
    ENTERPRISE  pet-events
    DESCRIPTION
        "Power Unit Failure event - Asserted."
    ::= 618246 

-- Event Sensor Type, Event Type, Event Offset (096F80h == 618368)
powerOffPowerUnitClear TRAP-TYPE
    ENTERPRISE  pet-events
    DESCRIPTION
        "Power Unit Power Off event - Deasserted."
    ::= 618368    
    
-- Event Sensor Type, Event Type, Event Offset (096F84h == 618372)
acLostPowerUnitClear TRAP-TYPE
    ENTERPRISE  pet-events
    DESCRIPTION
        "Power Unit AC Lost event - Deasserted."
    ::= 618372   
    
-- Event Sensor Type, Event Type, Event Offset (096F85h == 618373)
softPowerControlPowerUnitClear TRAP-TYPE
    ENTERPRISE  pet-events
    DESCRIPTION
        "Power Unit Soft Power Control Failure event - Deasserted."
    ::= 618373 
    
-- Event Sensor Type, Event Type, Event Offset (096F86h == 618374)
powerUnitFailureClear TRAP-TYPE
    ENTERPRISE  pet-events
    DESCRIPTION
        "Power Unit Failure event - Deasserted."
    ::= 618374

 -- Event Sensor Type, Event Type, Event Offset  
trapTestInstance TRAP-TYPE
    ENTERPRISE  pet-events
    DESCRIPTION
        "trap test"
    ::= 1208068 
    
--**************************************************************************
-- Cable/Interconnect Event event
--**************************************************************************
-- Event Sensor Type, Event Type, Event Offset (1B6F00h == 1797888)
cableInterconnect TRAP-TYPE
    ENTERPRISE  pet-events
    DESCRIPTION
        "Cable/Interconnect is connected - Asserted."
    ::= 1797888  

-- Event Sensor Type, Event Type, Event Offset (1B6F80h == 1798016)
cableInterconnectClear TRAP-TYPE
    ENTERPRISE  pet-events
    DESCRIPTION
        "Cable/Interconnect is connected - Deasserted."
    ::= 1798016  

--**************************************************************************
-- CPU CPUS event
--**************************************************************************
-- Event Sensor Type, Event Type, Event Offset (C0010Bh == 12583179)
cupsUpperNonRecoverableGoingHigh TRAP-TYPE
    ENTERPRISE  pet-events
    DESCRIPTION
        "Cups upper non-recoverable going high - Asserted."
    ::= 12583179   	
	
-- Event Sensor Type, Event Type, Event Offset (C00109h == 12583177)
cupsUpperCriticalGoingHigh TRAP-TYPE
    ENTERPRISE  pet-events
    DESCRIPTION
        "Cups upper critical going high - Asserted."
    ::= 12583177   
	
-- Event Sensor Type, Event Type, Event Offset (C00107h == 12583175)
cupsUpperNonCriticalGoingHigh TRAP-TYPE
    ENTERPRISE  pet-events
    DESCRIPTION
        "Cups upper non-critical going high - Asserted."
    ::= 12583175   
	
-- Event Sensor Type, Event Type, Event Offset (C0018Bh == 12583307)
cupsUpperNonRecoverableGoingHighClear TRAP-TYPE
    ENTERPRISE  pet-events
    DESCRIPTION
        "Cups upper non-recoverable going high - Deasserted."
    ::= 12583307  	
	
-- Event Sensor Type, Event Type, Event Offset (C00189h == 12583305)
cupsUpperCriticalGoingHighClear TRAP-TYPE
    ENTERPRISE  pet-events
    DESCRIPTION
        "Cups upper critical going high - Deasserted."
    ::= 12583305   
	
-- Event Sensor Type, Event Type, Event Offset (C00187h == 12583303 )
cupsUpperNonCriticalGoingHighClear TRAP-TYPE
    ENTERPRISE  pet-events
    DESCRIPTION
        "Cups upper non-critical going high - Deasserted."
    ::= 12583303 

-- Event Sensor Type, Event Type, Event Offset (146F00h == 1339136 )
alertTrapV1PowerButtonPressed TRAP-TYPE
    ENTERPRISE  pet-events
    DESCRIPTION
        "Power button pressed -Asserted."
    ::= 1339136 

-- Event Sensor Type, Event Type, Event Offset (146F80‬h == 1339264 )
alertTrapV1PowerButtonReleased TRAP-TYPE
    ENTERPRISE  pet-events
    DESCRIPTION
        "Power Button pressed -Deasserted."
    ::= 1339264 

-- Event Sensor Type, Event Type, Event Offset (1D6F07‬h == 1928967 )
alertTrapV1SysRestartUnknownAsserted TRAP-TYPE
    ENTERPRISE  pet-events
    DESCRIPTION
        "system restart unknown -Asserted."
    ::= 1928967 

-- Event Sensor Type, Event Type, Event Offset (1D6F87h == 1929095 )
alertTrapV1SysRestartUnknownDeasserted TRAP-TYPE
    ENTERPRISE  pet-events
    DESCRIPTION
        "system restart unknown -Deasserted."
    ::= 1929095 

-- Event Sensor Type, Event Type, Event Offset (1D7007h == 1929223 )
alertTrapV1SysRestartChassisCtrlAsserted TRAP-TYPE
    ENTERPRISE  pet-events
    DESCRIPTION
        "system restart Chassis Control command -Asserted."
    ::= 1929223 

-- Event Sensor Type, Event Type, Event Offset (1D7087h == 1929351 )
alertTrapV1SysRestartChassisCtrlDeasserted TRAP-TYPE
    ENTERPRISE  pet-events
    DESCRIPTION
        "system restart Chassis Control command -Deasserted."
    ::= 1929351 

-- Event Sensor Type, Event Type, Event Offset (1D7107h == 1929479 )
alertTrapV1SysRestartButtonAsserted TRAP-TYPE
    ENTERPRISE  pet-events
    DESCRIPTION
        "System Restart reset via pushbutton -Asserted."
    ::= 1929479 

-- Event Sensor Type, Event Type, Event Offset(1D7187h ==‬ 1929607 )
alertTrapV1SysRestartButtonDeasserted TRAP-TYPE
    ENTERPRISE  pet-events
    DESCRIPTION
        "System Restart reset via pushbutton -Deasserted."
    ::= 1929607 

-- Event Sensor Type, Event Type, Event Offset(1D7907‬h == 1931527 )
alertTrapV1SysRestartSoftAsserted TRAP-TYPE
    ENTERPRISE  pet-events
    DESCRIPTION
        "System Restart via soft reset -Asserted."
    ::= 1931527 

-- Event Sensor Type, Event Type, Event Offset (1D7987h == 1931655 )
alertTrapV1SysRestartSoftDeasserted TRAP-TYPE
    ENTERPRISE  pet-events
    DESCRIPTION
        "System Restart via soft reset -Deasserted."
    ::= 1931655    

 -- Event Sensor Type, Event Type, Event Offset (040104h == 262404)
 -- psuFanSpeedLowerNonRecoverablegoinglow TRAP-TYPE
 --     ENTERPRISE  pet-events
 --     DESCRIPTION
 --         "PSU_FanSpeed Lower Non-Recoverable going low -Asserted"
 --     ::= 262404 

 -- Event Sensor Type, Event Type, Event Offset (020104h == 131332) 
 -- psuVoutLowerCriticalgoinglow TRAP-TYPE
 --     ENTERPRISE  pet-events
  --    DESCRIPTION
  --        "PSU_Vout Lower Critical going low -Asserted"
 --     ::= 131332 
	
-- Event Sensor Type, Event Type, Event Offset (03010bh == 196875) 
 -- psuIinUpperNonRecoverablegoinghigh TRAP-TYPE
 --     ENTERPRISE  pet-events
 --     DESCRIPTION
  --        "PSU_Iin Upper Non-Recoverable going high -Asserted "
  --    ::= 196875
	
-- Event Sensor Type, Event Type, Event Offset (030109h == 196873) 
 -- psuIinUpperCriticalgoinghigh TRAP-TYPE
 --     ENTERPRISE  pet-events
 --     DESCRIPTION
 --         "PSU_Iin Upper Critical going high -Asserted "
 --     ::= 196873

-- Event Sensor Type, Event Type, Event Offset (030107h == 196871) 
 -- psuIinUpperNonCriticalgoinghigh TRAP-TYPE
 --     ENTERPRISE  pet-events
  --    DESCRIPTION
  --        "PSU_Iin Upper Non-Critical going high -Asserted "
  --    ::= 196871	

-- Event Sensor Type, Event Type, Event Offset (020104h == 131332) 
 -- psuVinLowerNonRecoverablegoinglow TRAP-TYPE
  --    ENTERPRISE  pet-events
  --    DESCRIPTION
 --         "PSU_Vin Lower Non-Recoverable going low -Asserted "
 --     ::= 131332	

-- Event Sensor Type, Event Type, Event Offset (020184h == 131460) 
 -- psuVinLowerNonRecoverablegoinglowclear TRAP-TYPE
 --     ENTERPRISE  pet-events
 --     DESCRIPTION
  --        "PSU_Vin Lower Non-Recoverable going low clear -Deasserted "
 --     ::= 131460	

-- Event Sensor Type, Event Type, Event Offset (030187h == 196999) 
 -- psuIinUpperNonRecoverablegoinghighclear TRAP-TYPE
 --     ENTERPRISE  pet-events
 --     DESCRIPTION
  --        "PSU_Iin Upper Non-Recoverable going high clear -Deasserted "
  --    ::= 196999	

-- Event Sensor Type, Event Type, Event Offset (030189h == 197001) 
 -- psuIinUpperCriticalgoinghighclear TRAP-TYPE
 --     ENTERPRISE  pet-events
 --     DESCRIPTION
 --         "PSU_Iin Upper Critical going high clear -Deasserted"
 --     ::= 197001

-- Event Sensor Type, Event Type, Event Offset (03018bh == 197003) 
 -- psuIinUpperNonCriticalgoinghighclear TRAP-TYPE
 --     ENTERPRISE  pet-events
 --     DESCRIPTION
 --         "PSU_Iin Upper Non-Critical going high clear -Deasserted "
 --     ::= 197003	

-- Event Sensor Type, Event Type, Event Offset (020184h == 131460) 
 -- powerSupplyFailuredetected TRAP-TYPE
 --     ENTERPRISE  pet-events
 --     DESCRIPTION
 --         "Power Supply Failure detected -Asserted"
 --     ::= 131460
	
-- Event Sensor Type, Event Type, Event Offset (020104h == 262532) 
 -- pSUVoutLowerCriticalgoinglowclear TRAP-TYPE
 --     ENTERPRISE  pet-events
 --     DESCRIPTION
 --         "PSU Vout Lower Critical going low clear -Deasserted "
 --     ::= 262532
	
END
